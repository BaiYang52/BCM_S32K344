# Safety Manual

# Specification
- ReqIF.ForeignRevision: 5315117
- ReqIF.ForeignReleaseStatus: DRAFT
- ReqIF.Name: Safety Manual

## b8e47e774ef52dedfcf8586d8b8dcb40e36757468762f0a6725831b54e036be2
Safety Manual
- ObjectType: DocItem

## 32f60fa2dcd0a8162184bce05dad12201844efe93c75b80258850672aff0bd4d
| Version | Date | Author | Remarks |
| --- | --- | --- | --- |
| 1.00.00 | 2015-11-13 | Jonas Wolf | Initial creation |
| 1.01.00 | 2015-12-18 | Jonas Wolf | Information about ASIL added. |
| 1.02.00 | 2016-01-29 | Jonas Wolf | Improvements in formulation. |
| 1.03.00 | 2016-02-25 | Jonas Wolf | Improvements in formulation. |
| 1.03.01 | 2016-03-30 | Jonas Wolf | Review findings incorporated. |
| 1.03.02 | 2016-05-13 | Jonas Wolf | Added hint on hardware-software integration (SMI-4). |
| 1.03.03 | 2016-07-20 | Hartmut Hoerner | Added SMI related to interrupt handling. |
| 1.04.00 | 2016-09-02 | Jonas Wolf | Added TSR-101876 for data consistency. |
| 1.04.01 | 2016-09-19 | Jonas Wolf | Clarifications on SMI-100 and SMI-19. |
| 1.04.02 | 2016-12-02 | Jonas Wolf | Version of referenced document fixed. |
| 1.05.00 | 2017-02-24 | Jonas Wolf | Modified SMI-18: checks need to be enabled per component as well. |
| 1.06.00 | 2017-05-05 | Jonas Wolf | Added SMI-36039: Pointer validity passed to call-outs. Added SMI-36041: Information on Beta-ESCANs. Update of versions of referenced documents. Section 1.1.5 clarified. |
| 1.07.00 | 2017-06-20 | Jonas Wolf | Update of TSRs from TSC (update is backward compatible) Added info on this version history. Fixes of typos. |
| 1.07.01 | 2017-08-18 | Jonas Wolf | Added information on TCL for MSSV and RTE Analyzer. |
| 1.08.01 | 2017-11-10 | Jonas Wolf | Added information on TCL for post-built tool chain. Added information that OS timing protection is only a partial replacement for a watchdog. |
| 1.09.00 | 2018-01-11 | Jonas Wolf | Added details to SMI-16 for interfaces between MICROSAR components. |
| 1.09.01 | 2018-01-30 | Jonas Wolf | Fixed typo in SMI-16. |
| 1.09.02 | 2018-05-03 | Jonas Wolf | Added information on SMI-12. |
| 1.10.00 | 2018-11-16 | Jonas Wolf | Update of technical safety concept. More info on SMI-99. Added SMI-246328. |
| 1.11.00 | 2019-06-25 | Jonas Wolf | Update of technical safety concept. |
| 1.12.00 | 2020-03-16 | Jonas Wolf | Adding SMI-428133 for VCA. Adding clarification for SMI-8. |
| 1.13.00 | 2020-06-03 | Jonas Wolf | Update of technical safety concept. Adding SMI-494148 and SMI-246328 and clarifications for systems with safety-related availability requirements. |
| 1.14.00 | 2020-09-08 | Jonas Wolf | Make history more precise and improve wording of SMI-494148. |
| 1.15.00 | 2021-02-18 | Jonas Wolf | Make document structure more precise. Improve details on SMI-14 and SMI-4. |
| 1.16.00 | 2021-03-08 | Jonas Wolf | Update of information on timing guarantees and TSR-6. |
| 1.16.01 | 2021-03-12 | Jonas Wolf | Update with review comments. |
| 1.16.02 | 2022-04-20 | Vibhu Layal | Added information to SMI-9. |
- ObjectType: DocItem

## 4e6b98cd4722df1c8f1def73b80d4e2c24d0aa1148708bfac0be631fe303fc23: General Part
- ChapterNumber: 1
- ObjectType: DocItem

### dd731d28d2e4ad13ac52093542e0c2a1eca1e7770807b8fde3ef4703a01ba712: Introduction
- ChapterNumber: 1.1
- ObjectType: DocItem

#### 6f88f70d2a238bd92032099724fbad968c1be2926dfdfcedbdd21bd4d527ca31: Purpose
- ChapterNumber: 1.1.1
- ObjectType: DocItem

##### 4daeeaaa6b86dc259bcc656e1b6da071a0b18249230ed68e7e15045862f958e4
This document describes the assumptions made by Vector during the development of MICROSAR Safe as Software Safety Element out of Context (SEooC). This document provides information on how to integrate MICROSAR Safe into a safety-related project.
- ForeignTraceId: OBJ537
- ForeignAlternativeId: OBJ-53B0D376-4213-4102-8055-A0DAEAB369C0
- ObjectType: TRACE_ITEM

##### 3e69767094027cbad8dee8142387e8d7a54e5d6daf6f09ddf0b415d043d543b0
This document is intended for the user of MICROSAR Safe. It shall be read by project managers, safety managers, and engineers to allow proper integration of MICROSAR Safe.
- ForeignTraceId: OBJ535
- ForeignAlternativeId: OBJ-19F79639-32B3-47CA-9B22-9534C10B98F2
- ObjectType: TRACE_ITEM

#### 1e66be8845759c4ff35ebc41cdeeef4cc6809ee778d40ac1d53284bc45f396be: Scope
- ChapterNumber: 1.1.2
- ObjectType: DocItem

##### 03f27f935d8559faf5dc744c55538f32e42854484afd4f486c3f96f0f3c8c4b9
This document adds additional information to the components that are marked with an ASIL in the delivery description provided by Vector. Neither QM Vector components, nor components by other vendors are in the scope of this document.
- ForeignTraceId: OBJ536
- ForeignAlternativeId: OBJ-00B464C4-9B99-40B7-8489-45FFD8C372BF
- ObjectType: TRACE_ITEM

##### 654db0b0f37c7a1ce608acafd15bff577a8763d8a6780831c3a8a9d8ca0f0b4e
Vector assumes that hardware and compiler manuals are correct and complete.
Vector uses the hardware reference manuals and compiler manuals for the development of MICROSAR Safe. Vector has no means to verify correctness or completeness of the hardware and compiler manuals.
Example information that may be critical from these manuals is the register assignment by compiler. This information is used to built up the context that is saved and restored by the operating system.
The compiler manual from the compiler version specified for the project is considered. The considered hardware manuals are documented in the Technical Reference of the hardware-specific component.
- ObjectType: DocItem

##### d3240d6d41545e07448b8f564b6f8e324406ff83100d4a4318449cb08eeb6c1f
A general description of Vector's approach to ISO 26262 is described in [2]. This document is available on request.
- ObjectType: DocItem

#### 397599652561a234966ba12f35fa09e711646feb9ae143026748ab605bfde253: Definitions
- ChapterNumber: 1.1.3
- ObjectType: DocItem

##### 1e2f3437d924601613a4c9e31a841de21a3460aec98865d82f62e341831ef435
The words shall, shall not, should, can in this document are to be interpreted as described here:
1. Shall means that the definition is an absolute requirement of the specification.
2. Shall not means that the definition is an absolute prohibition of the specification.
3. Should means that there may exist valid reasons in particular circumstances to ignore a particular definition, but the full implications must be understood and carefully weighed before choosing a different course.
4. Can means that a definition is truly optional.
- ObjectType: DocItem

##### 7b6ccd8dbe016da2e3646c12f246904cdf05aa8db9b13d523051816a6dbefa86
Each requirement in this specification has a unique identifier beginning with SMI. This identifier is semantically the same even for different Safety Manuals provided by Vector.
- ObjectType: DocItem

##### 194b4d5cdaefd1eda14247d015a5d9cf91c76f8670db31ac237b3ae8bdcbb99d
The user of MICROSAR Safe can deviate from all constraints and requirements in this Safety Manual in the responsibility of the user of MICROSAR Safe, if equivalent measures are used.
If a measure is equivalent can be decided in the responsibility of the user of MICROSAR Safe.
- ObjectType: DocItem

#### 08c02123719d1d872758fde2162b77423d32a0d157fe219dc3dc7fb4d4c46a80: References
- ChapterNumber: 1.1.4
- ObjectType: DocItem

##### 84f042103305e055318f058f92f2317307a004f4e3742156e7130f9132d146e0
| No. | Source | Title | Version |
| --- | --- | --- | --- |
| [1] | ISO | ISO 26262 Road vehicles — Functional safety (all parts) | 2011/2012 |
| [2] | Vector | ISO 26262 Compliance Document | 1.3.2 |
| [3] | Vector | MICROSAR Safe Product Information | As provided with the quote |
| [4] | Vector | MICROSAR Safe Silence Verifier Technical Reference | As provided with the delivery |
| [5] | Vector | Vector Code Analyzer Technical Reference | As provided with the delivery |
- ObjectType: DocItem

#### 80737d6270ccf394336a6129a228a2c67012eb819217f3263cfa2b871e2f7d66: Overview
- ChapterNumber: 1.1.5
- ObjectType: DocItem

##### f9fb6333e69d4dadbf4b233fe9e396b5254f26134f97b1da83d19f92ca482187
This document is automatically generated for a delivery. The content of this document depends on the components (incl. their version) and used hardware (e.g. microcontroller or external hardware) in the delivery. This document is thus valid only for the delivery from Vector that it is included in. The version history above only reflects changes in the component independent part of the Safety Manual.
- ObjectType: DocItem

##### 37e81a4844f21592eb73cbaece95d35ad1e2302d8894d4db244552b49577ed9b
The structure of this document comprises:
- a general section that covers all assumptions and constraints that are always applicable, and
- at least one section for each ASIL component that covers its constraints and necessary verification steps. The section for a component is identified by its module abbreviation.
- ForeignTraceId: OBJ539
- ForeignAlternativeId: OBJ-CA19DAA4-4C03-4070-8796-ABD2A5DB10C9
- ObjectType: TRACE_ITEM

##### eaf7ba880aab7760d7ed17b4e67b0919b4629fcd04ae07b1ad1842138443d084
Vector's assumptions on the environment of the MICROSAR Safe components as well as the integration process are described.
- ForeignTraceId: OBJ540
- ForeignAlternativeId: OBJ-A0E81520-DEB4-4CD0-A665-59F09D861283
- ObjectType: TRACE_ITEM

##### 6815816294c3cf065c78a2d094bdc2a3b6a1890daac13a96e67b5d8a4801e95b
Vector developed MICROSAR Safe as Safety Element out of Context for projects demanding ASIL D software. All requirements in this document apply independently from the actual highest ASIL of the project (unless otherwise stated).
- ObjectType: DocItem

##### 90277c48a227bfb068552a01aefb44a2c8e2e30ad679c8e1aef8a7d9ec502338
MICROSAR Safe comprises a set of components developed according to ISO 26262. These components can be combined - together with other measures - to build a safe system according to ISO 26262.
Please read the Product Information MICROSAR Safe [3] first.
- ObjectType: DocItem

### 33ba8cb573bd854bcc02c83ac3db69aeaa8ca50ae6cf20a2f9a9a31c5bdd4136: Safety Concept
- ChapterNumber: 1.2
- ObjectType: DocItem

#### 5687016c826ffa6ba0c16c52d81a7c3a6af09e590ab4ddc3266632607d9bd45f
It is assumed that the user of MICROSAR Safe is responsible for overall system safety. MICROSAR Safe can provide parts of safety mechanisms to its user. It is also assumed that the user of MICROSAR Safe verifies the robustness and effectiveness of the safety mechanisms within its system based on the configuration of MICROSAR Safe.
- ObjectType: DocItem

#### 00fd5009a3cea4106c54276916ae957d7c57e727b0707298ce73ee4e7ad305e7: Technical Solution
- ChapterNumber: 1.2.1
- ObjectType: DocItem

##### 0d3630e8cb90088e20f6073010b12488dc34b7a2f56341ab13efcf5c7fc6a840
Possible hardware faults (transient or permanent) are detected and handled by the application (user of MICROSAR Safe) according to the required ASIL necessary for the project.
This also implies protection against Single Event Upsets (SEUs) in volatile and non-volatile memory, as well as faults in registers and processing logic.
- ObjectType: DocItem

##### fbbdb8e8d7b93790156ae3df2ad3d08cc9af43e64b60d23937d3750035dc3aa1
The hardware manual is assumed to be complete and correct.
- ObjectType: DocItem

##### c2738ac8869973b76b8884de645d4fb71b8ede906a780d9b8d4b9414ac93dc73
MICROSAR Safe does not implement mechanisms to mitigate random hardware faults. Instead, MICROSAR Safe relies on hardware mechanisms, such as ECC memory and lock-step cores. For systems with safety-related availability requirements sufficiently reliable hardware or redundancy in hardware is assumed to cover hardware faults. Such hardware faults might e.g. occur during communication between the different parts of the redundant system.
- ObjectType: DocItem

##### ad4abd6bcfc699fe5ed49adc12f7eb5013393224122a832cababd53363fb378a
Note that multi-core controllers with cores that provide different levels of diagnostic coverage (lock-step/non-lock-step cores) are considered during development of the MICROSAR Safe operating system.
However, they also require a detailed analysis of core interdependency by the user of MICROSAR Safe.
- ObjectType: DocItem

##### ceee23abd460399eaf923172b32f79c1db888fe2be4f12734ad97d55bf13696d
It is assumed that systematic hardware faults are handled on system or application level by the user of MICROSAR Safe.
- ObjectType: DocItem

##### 22791150d6275028d3e1c1933384e5d53ab9466787e80556f277abfeb491e79f
The Safety Manual of the hardware MICROSAR Safe controls is used during development. The respective part of MICROSAR Safe Safety Manual describes if MICROSAR Safe implements safety mechanisms required by the Safety Manual of the hardware it controls.
- ObjectType: DocItem

##### c853b95570986f11dd88ac494fd7e3613d35a54b9aecbd03c3e62d8061edce04
Systematic faults in functionality that is allocated an assumed TSR in MICROSAR Safe are prevented by implementation of an ISO 26262-compliant development process.
It is assumed that development according to an ISO 26262-compliant development process implicitly ensures freedom from interference with respect to memory. I.e. MICROSAR Safe components only write within bounds of memory that they have ownership of.
- ObjectType: DocItem

##### 87f037747418dba6d6bd130def4b673ec48912b8a2414a6a3dac11c5216039fb
For systems with safety-related availability requirements, it is assumed that systematic faults in software in the chain of events must be avoided. Thus, the complete software in the chain of events must implement safety requirements (see e.g. TSR-111108). It is already ensured that no out-of-bounds memory write accesses are performed (see above). Invalid read accesses cannot interfere in memory, since they do not modify memory even if they trigger a trap.
However, the software in the chain of events must also perform its function within a bounded time. Therefore, MICROSAR Safe provides a real-time scheduler in the operating system and the corresponding Runtime Environment (Rte) ensures scheduling as specified and configured by the user of MICROSAR Safe (see TSR-6).
Moreover, components of MICROSAR Safe can provide a bounded execution time of their functionality. A finite execution time analysis (FETA) is performed for those components. This analysis ensures that components of MICROSAR Safe do not disturb execution flow of other modules by occupying CPU resources indefinitely, i.e. it ensures freedom from interference with respect to timing. This analysis is always a worst-case estimation. The information if a component provides this guarantee, can be found in the respective part of the Safety Manual of MICROSAR Safe. A Worst Case Execution Time (WCET) analysis still has to be performed by the user of MICROSAR Safe to evaluate if timing requirements in their system can be achieved.
Invalid read accesses to memory are not an issue in the first place, since the trap handler also is assumed to have a bounded runtime. If the upper bound of execution time of an algorithm in MICROSAR Safe components depends on the validity of read accesses this is analyzed during development of those components.
Invalid read accesses could also impact the functionality of MICROSAR Safe components. However, the correctness of the used data is ensured by the testing activities during the development of MICROSAR Safe and the used defensive programming.
- ObjectType: DocItem

##### 661e5c163175005820b259566c1ea6f8e7d6f6744caf7d8e00258029b8354e9f
MICROSAR Safe does not implement redundant (inverted) data storage to mitigate software faults.
- ObjectType: DocItem

##### 0f58f8189cd3a5e850a1a3e46b79ed7ac15f0dfd49388fdc2b6570d887e96a41
It is assumed that software with a different integrity level is separated using a memory protection unit (MPU) (see also TSR-7).
The user of MICROSAR Safe has to ensure that write access to the same memory parts is only possible for software of the same or higher integrity level.
- ObjectType: DocItem

##### 8624919ee55ba2ca9370fbf143311797b9d9d24af68f2409c5792db8cba3f7cd
Depending on the requirements of the item, timing and program flow must be monitored. MICROSAR Safe provide mechanisms to implement this monitoring (see also TSR-13, TSR-14 and TSR-15).
MICROSAR Safe does not automatically monitor itself for intended timing and program flow.
For systems with safety-related availability requirements, it may be required to avoid interference in time and not only to detect it using e.g. a watchdog. It is assumed that the user of MICROSAR Safe adequately ensures freedom from interference with respect to time for this use-case by configuration of MICROSAR Safe.
- ObjectType: DocItem

##### 54b8fd1efee1fe6156f2f68bff8eef44958dc8b32407a23edbf4b39601a36ea2
MICROSAR Safe components without allocated safety requirements are developed according to an ISO 26262-compliant development process to provide an argument for coexistence.
- ObjectType: DocItem

##### 7607e431f1586b0590226ea4e0f85be7cf17616dba06b53df9a4ce1c13a04a95
If safety requirements are implemented in components of MICROSAR Safe, Vector ensures that they are locally non-complex.
For locally non-complex components no diverse implementation of algorithms is designed.
- ObjectType: DocItem

#### aafc39067367cf10a4b3b075f7d5328bab08affa5ca96baf4faf6f22bba1022c: Tool Confidence
- ChapterNumber: 1.2.2
- ObjectType: DocItem

##### 76d6b38665cded08dfce721420803d5ab02b5a09bad5a429290506cdcc2e7cea
MICROSAR Safe must be configured using the DaVinci tools. MICROSAR Safe must be compiled by using a compiler for the target hardware.
These tools must be evaluated with respect to their impact on functional safety by the user.
- ObjectType: DocItem

##### 63ec5225c65315d3049b33f4483975e29b67bc524d7c17dd912b0f077331d69f
It is assumed that the user of MICROSAR Safe evaluates and qualifies the defined compiler (incl. options) and linker according to ISO 26262 Part 8 Clause 11.
- ObjectType: DocItem

##### a451a88864295f994976eb5138f982ff03510d712f0821a54ef0cf72817abb70
The DaVinci Developer and DaVinci Configurator are assumed to have an impact on functional safety. In the first place, only a tool error detection level of two can be expected.
The resulting tool confidence level (TCL) would require a qualification of those tools.
- ObjectType: DocItem

##### 62ccfb4fac4175e2e57d008481028e499970e8c86419a3c02a0a11acf8a5e1f7
To ensure freedom from interference with respect to memory for the BSW, Vector provides the MICROSAR Safe Silence Verifier (MSSV).
- ObjectType: DocItem

##### 0ffd7da9903a36e0077871e40f950dff7e7b70356356ae3f290c6d82a2139535
To ensure freedom from interference with respect to memory and to detect additional faults that may have been introduced by the DaVinci tools for the RTE, Vector provides the RTE Analyzer.
- ObjectType: DocItem

##### f6d4af2f987e61b48cd30cc339c10fe0ede52f1ad9810643514e57accaea451c
If MSSV and RTE Analyzer are used according to their Technical References and the Safety Manual, the tool confidence level for the DaVinci tools can be reduced to TCL1 by the user of MICROSAR Safe.
- ObjectType: DocItem

##### b76b33217b3cc9720a4a0e0c69a5a91020ef6fcb6a8693f8a3b62a74b5d09e21
Tools by Vector do not implement mechanisms to handle hardware faults on the host development computer.
- ObjectType: DocItem

### 34b006c63811ceb2febab7a19bfcef7af870c5102d58dae0c86312fec0382843: Assumed Safety Requirements of MICROSAR Safe
- ChapterNumber: 1.3
- ObjectType: DocItem

#### 9f3ae5e384309102621368a4f4e8a01b8f54e141f2c4ca07cd3bae902640d787
The items listed in this section are the assumed technical safety requirements on the Safety Element out of Context MICROSAR Safe.
These requirements are expected to match the requirements in the actual item development.
- ObjectType: DocItem

#### 45462c48807a12f85f02661261ca2840d80f9d479751ffa071729126c354fd60
All technical safety requirements (TSRs) are assigned an ASIL D (unless otherwise stated) to service as many projects as possible.
- ObjectType: DocItem

#### 644cb8bcc0c6bd8c6760295b3683873ac05c30db1ceb306755bc1ad7e101083f
<Unparsable text>
- ObjectType: DocItem

#### 4b5d2793ef3f5457f2866580d9f8969109b2349c6d97815a851152dcf41fd3f1
<Unparsable text>
- ObjectType: DocItem

#### f3f663ac41aa78e7247bf8cde4fd1a88ac0cf3d1d84a0b61d19d321f8275cedd
The Safety Manual provided with a delivery shows the details on the support of a safety requirement on component level for a specific version.
- ObjectType: DocItem

#### fe5fc28d12a5de304f73b6afde7ced2df9efd600cd5bc6bd634f8faded418811: Initialization
- ChapterNumber: 1.3.1
- ObjectType: DocItem

##### ff0b1515384ca1fa868154ff76aae81771bf14fa30421e59dcfac460b8381d88
TSR-1 MICROSAR Safe shall provide a mechanism to initialize itself and its controlled hardware.
It is sensible for safety-related systems to start performing potentially hazardous actions only in a defined and intended state.
For example, adequate setup of clocks may be required to reach required fault tolerant times.
Components of MICROSAR Safe initialize their variables. For post build selectable and post build loadable configurations MICROSAR Safe components use a consistent and defined set of configuration data.
Hardware-specific components of MICROSAR Safe describe in their Technical References what hardware units are controlled.
The user of MICROSAR Safe shall ensure that initialization functions of MICROSAR Safe are called in the right order and at the right point in time.
The user of MICROSAR Safe is also responsible for the startup code and main function.
- ObjectType: DocItem

#### 5b583a0c1f2e8410d518b57716960f35b83a3d3c46b3442a1c352c8830cfa425: Data Consistency
- ChapterNumber: 1.3.2
- ObjectType: DocItem

##### 532b4ea1fddc48e2876b181d163836e4aa284b87e050e69d3c615d6ba19441ab
TSR-101876 MICROSAR Safe shall provide mechanisms to ensure data consistency.
Concurrent access to resources (e.g. variables) from e.g. task and interrupt level, may lead to data inconsistencies.
MICROSAR Safe provides functions to enable or disable interrupts, spin-locks, resources or abstractions (i.e. exclusive areas) to enable the user of MICROSAR Safe to ensure data consistency.
MICROSAR Safe will not unintentionally enable or disable the mechanisms to ensure data consistency.
MICROSAR Safe also uses this functionality in its own components to ensure data consistency.
- ObjectType: DocItem

#### 3e2989f150d38933869bf14f7ce6836d8aec255bd9878162c7851fe5f622057d: Non-volatile Memory
- ChapterNumber: 1.3.3
- ObjectType: DocItem

##### 58f3a6a56b048a5e58447ad0bad3ff4f9cdd124cd3fa59e67e8b36a0abd21573
TSR-4 MICROSAR Safe shall provide a mechanism to store data in non-volatile memory.
Calibration or other application data may be safety-related, i.e. if there is data available from non-volatile memory it must not be corrupted by either software or hardware.
MICROSAR Safe implements an end-to-end protection in the Non-volatile RAM Manager (NvM) to ensure that data is neither corrupted nor masqueraded in either software or hardware.
Note that hardware may not even start storing data in non-volatile memory or loose it at any time.
Availability of data is, thus, not guaranteed. Availability may be increased by redundantly storing data in non-volatile memory.
The user of MICROSAR Safe must handle unavailability of data on application level.
- ObjectType: DocItem

##### 03f49d52a55f8d68c30e52efa2b2b23c53522818f129a39081d9d3101e7966cf
TSR-5 MICROSAR Safe shall provide a mechanism to retrieve data from non-volatile memory.
Calibration or other application data may be safety-related, i.e. if there is data available from non-volatile memory it must not be corrupted by either software or hardware.
MICROSAR Safe implements an end-to-end protection in the Non-volatile RAM Manager (NvM) to ensure that data is neither corrupted nor masqueraded in either software or hardware.
Note that hardware may not even start storing data in non-volatile memory or loose it at any time.
Availability of data is, thus, not guaranteed. Availability may be increased by redundantly storing data in non-volatile memory.
The user of MICROSAR Safe must handle unavailability of data on application level.
Note that if data is written more than once and the latest data in the non-volatile memory gets corrupted, older (uncorrupted) data may be returned to the user of MICROSAR Safe.
- ObjectType: DocItem

#### e1af2248ed7ebab7bd8c9e619ad8249f42e7f8d0206b03e4adbc2b5bc6f14e38: Hard Real-time Scheduling
- ChapterNumber: 1.3.4
- ObjectType: DocItem

##### aa32452d1ee1adece128f6e6bbe91f40e9ea96b035135c8e40cc12ad279e6b3e
TSR-6 MICROSAR Safe shall provide hard real-time scheduling properties.
Hard real-time scheduling is not required for safety in the first place, since deadline violations can usually be detected and a safe state entered.
However, hard real-time scheduling may support argumentation in some cases.
For systems with safety-related availability requirements hard real-time scheduling properties are essential for the software that needs to stay operational.
The operating system of MICROSAR Safe implements fixed priority scheduling and the immediate priority ceiling protocol specified by AUTOSAR to guarantee hard real-time scheduling properties.
The runtime environment of MICROSAR Safe (SafeRTE) schedules runnables as configured by the user of MICRSOR Safe.
Note that safety-related availability requirements on a system usually require a second independent channel of control.
Note that safety-related availability requirements require analyses of the worst-case execution time (WCET) of the software that needs to stay operational. These analyses are expected from the user of MICROSAR Safe.
- ObjectType: DocItem

#### 55140171da3c30b64fb58b6c4a8f65614cac62b542c081f9c3eb4a96464b7e3e: Memory Protection
- ChapterNumber: 1.3.5
- ObjectType: DocItem

##### 4a8187a1da5465369bbf9b0348f8b2e3567f7184ce715d2f91c0d55dd811252b
TSR-7 MICROSAR Safe shall provide mechanisms to protect software applications from unspecified memory access.
Partitioning in software is often introduced because of different quality levels of software and different responsibilities of software development on one ECU.
Memory partitioning relies on the memory protection unit (MPU) in hardware for the effectiveness of the mechanism.
MICROSAR Safe configures exactly the configured memory access rights for each task and ISR at the hardware interface of the MPU.
Note that MICROSAR Safe does not necessarily control all available protection units (e.g. system MPUs or peripheral protection units).
The user of MICROSAR Safe is responsible for adequate configuration of the memory partitions.
- ObjectType: DocItem

#### d140da915a715f76e1b6b226c04b432ee0abbf4438b92481e78936dc3279a664: Communication
- ChapterNumber: 1.3.6
- ObjectType: DocItem

##### 9d0b92e5739fab8b159ccfe42353092219b07d7de5fbbcf3acb8f6b8578d8080: Inter ECU Communication
- ChapterNumber: 1.3.6.1
- ObjectType: DocItem

###### e4cef3d5a57b69842013dc7c279d16668736e0149653482520f96bcbfaa1d167
TSR-10 MICROSAR Safe shall provide mechanisms to protect communication between ECUs.
Communication between ECUs may be corrupted, unintentionally replayed, lost or masked. To protect against these failure modes MICROSAR Safe provides the end-to-end (E2E) protection mechanism defined by AUTOSAR.
MICROSAR Safe detects repetition, loss, insertion, masking, reodering and corruption of messages between ECUs.
MICROSAR Safe allows the usage of cyclic redundancy checks (CRCs) and cryptographic algorithms to protect the integrity of messages between ECUs.
CRCs provide a certain hamming distance given a polynomial and maximum data block size.
Cryptographic hash functions or message authentication codes (MACs) provide a probabilistic statement on data corruption detection depending on the hash function or MAC, data block size and hash value size.
The user of MICROSAR Safe is responsible for the selection of the E2E profile or algorithm that is adequate to the requirements of the item development.
MICROSAR Safe does not reject messages with a valid CRC, hash or MAC. This is required for systems with safety-related availability requirements to claim reliability of a single channel. MICROSAR Safe relies on the integrity of the underlying hardware for e.g. verification of a MAC if configured.
- ObjectType: DocItem

###### 1a7ba178a476576fe6ff51fbf4e1d33b34c325b0886c5104fc0f9e3f0ac843fc
TSR-111108 MICROSAR Safe shall provide mechanisms to communicate between ECUs.
End-to-end protection ensures that repetition, loss, insertion, masking, reordering and corruption of messages between ECUs can be detected. These kinds of faults can be introduced by hardware or software.
For systems with safety-related availability requirements it is required to eliminate software as a source of the above-mentioned faults on sender and receiver side.
Thus, MICROSAR Safe does not unintentionally repeat, drop, insert, mask, reorder or corrupt messages. MICROSAR Safe might drop messages that have been corrupted by hardware faults, e.g. corruption by electromagnetic interference on the bus.
Usage of end-to-end protection is still required to ensure protection against hardware faults.
- ObjectType: DocItem

##### 40828613ced2e4f6c90adb594c0cd2cfd49db8d7b576e8f670e6456b20c3ae61: Intra ECU Communication
- ChapterNumber: 1.3.6.2
- ObjectType: DocItem

###### 973309984554d1d80c7ff42c8fb9d14bf54b4e2cd260573f93848f64def9fcaf
TSR-16 MICROSAR Safe shall provide mechanisms to communicate within its applications.
Software components need to communicate in order to fulfill their task.
MICROSAR Safe provides mechanisms to communicate within OS applications without end-to-end protection.
MICROSAR Safe does not unintentionally repeat, delay, insert, mask, corrupt or loose data communicated within OS applications.
MICROSAR Safe assumes protection of the memory against random hardware faults by the system, e.g. via ECC RAM and lock-step mode.
- ObjectType: DocItem

###### f64d32099bca9e804f47e94633962aaf4e5f34999f29eccdc7411c3b11eb48fc
TSR-12 MICROSAR Safe shall provide mechanisms to communicate between its applications.
Mixed ASIL or multi-core systems need to exchange safety-related information between applications.
MICROSAR Safe provides mechanisms to communicate between OS applications without end-to-end protection.
MICROSAR Safe does not unintentionally repeat, delay, insert, mask, corrupt or loose data communicated between OS applications.
MICROSAR Safe assumes protection of the memory against random hardware faults by the system, e.g. via ECC RAM and lock-step mode.
- ObjectType: DocItem

#### 7c66f58244ed7e3ba892a4fdcb577c605ce1d8aa3fbb75969fa0b47242979a72: Monitoring of Software
- ChapterNumber: 1.3.7
- ObjectType: DocItem

##### 6be66e33ba359dc4a4604734240642a8669852256e7b35377c28e5133ed19f7f
MICROSAR Safe provides monitoring mechanisms to supervise correct execution of software. These mechanisms must be configured by the user of MICROSAR Safe according to the requirements within the context of the item development.
- ObjectType: DocItem

##### 1046e5de754c0c4b95e28a3b92a6fc257d6294805893d4cd61b7fcf4df948840
TSR-13 MICROSAR Safe shall provide a mechanism to detect faults in program flow.
Program flow can be corrupted by random hardware faults or software faults.
The user of MICROSAR Safe can configure a graph of the logical program flow that is then supervised by MICROSAR Safe. A transition from one checkpoint to another that is not allowed is detected.
- ObjectType: DocItem

##### 02c1de4fba8bc5aa928a7e74e818c2dd67d066a3ca08e7460a82616e2f6d0994
TSR-14 MICROSAR Safe shall provide a mechanism to detect stuck software.
Alive monitoring is used to reset the software or controller in case it is unresponsive.
The user of MICROSAR Safe can configure entities that need to regularly report their alive status that is then supervised by MICROSAR Safe. Omission of a regular report is detected.
- ObjectType: DocItem

##### 972bb434b36ae5436b39216d6b77cc68d330fd72b49cfeda85a6454d916738f8
TSR-15 MICROSAR Safe shall provide a mechanism to detect deadline violations.
Deadlines are important to reach a safe state within the defined fault tolerant time interval.
The user of MICROSAR Safe can configure a tolerable time interval for each transition in a logical program flow graph that is then supervised by MICROSAR Safe. Violation of a deadline is detected.
- ObjectType: DocItem

##### b69e42ef1dbadb5dcdf5d810c5d349d4632f81be95b7f4e2bdb88d84ae419942
TSR-8 MICROSAR Safe shall provide a mechanism to detect time budget violations.
Budgets for task execution times, inter-arrival times and locking times allow to identify the originator of a deadline violation.
The user of MICROSAR Safe can configure budgets for execution times of tasks and category 2 ISRs, inter-arrival times and duration of locks (e.g. resource or interrupt locks) that are then supervised by MICROSAR Safe.
Exhaustion of budgets is detected.
- ObjectType: DocItem

##### b3287d22f9d9c35157510719233b432a1c0a2370987541de4e4d12d82c0fbf07
TSR-9 MICROSAR Safe shall provide a mechanism to terminate software applications.
Terminating a complete OS application may be used as a safety mechanisms to mitigate a software fault within this OS application. This terminated OS application typically comprises QM software.
MICROSAR Safe terminates exactly the requested OS application and only upon request.
Note that MICROSAR Safe will not terminate OS applications automatically without configuration or request.
- ObjectType: DocItem

#### dd9535c43c9b66fb470b39509ec24d56fea39053cdd3820aff94eb62b06e77f0: Operating Modes
- ChapterNumber: 1.3.8
- ObjectType: DocItem

##### 6970de69966e31b680bfac971ebd8a489f5e8bd67ea4c79bf63a6ede42a1ed7e
TSR-100551 MICROSAR Safe shall provide a mechanism to switch between operating modes.
Fault detection and mitigation often result in a degraded or safe state.
MICROSAR Safe does not unintentionally switch between operating modes. MICROSAR Safe switches to exactly the requested operating mode.
- ObjectType: DocItem

#### 0f7f02c94ea48ada3b9b8cf7b312954e91b7e1accf41723ea0f0d301a5cf28bd: Peripheral In- and output
- ChapterNumber: 1.3.9
- ObjectType: DocItem

##### bb176c428cc95554a83db0399cbbff9f28989656662d9bc46edcdcd69caa2734
TSR-17 MICROSAR Safe shall provide a mechanism to read input data from peripheral units.
Input of data from microcontroller peripheral units is required to implement almost any safety-related system.
MICROSAR Safe provides the data read from peripheral units without corruption or unintentional delay.
MICROSAR Safe does not unintentionally reorder nor masquerade data read from peripheral units.
Note that the peripheral hardware may not provide sufficient diagnostic coverage without redundant input.
For example, DIO and SPI drivers provided by Vector support the reading input data from peripheral units as safety requirement.
- ObjectType: DocItem

##### 725e9186057a369e821547b8261ffa3af5efd0ead5c286fa3758cb2edca6eee2
TSR-18 MICROSAR Safe shall provide a mechanism to write output data to peripheral units.
Output of data from microcontroller peripheral units is required to implement almost any safety-related system.
MICROSAR Safe writes the data provided at the software interfaces without corruption or unintentional delay.
MICROSAR Safe does not unintentionally trigger peripheral output units.
MICROSAR Safe does not unintentionally reorder nor masquerade data read from peripheral units.
Note that the peripheral hardware may require additional mechanisms on application or system level to ensure sufficient safety.
For example, DIO and SPI drivers provided by Vector support the output of data to peripheral units as safety requirement (e.g. to trigger external watchdogs or switch actuation paths).
- ObjectType: DocItem

#### 438f885169c8e0c79b7cbd0f976dce79d2dddf7ff69893052da8cef3e149087b: Time Synchronization
- ChapterNumber: 1.3.10
- ObjectType: DocItem

##### 0dbc59005f7d53d343b66c07e28de201da5a11c30f8e2764dcebdea63c59044f
TSR-111109 MICROSAR Safe shall provide a mechanism synchronize time between different ECUs.
For advanced driver assistance systems (ADAS) data from different sensor ECUs must be synchronized to perform sensor fusion. It is necessary that all participating ECUs must have a synchronized time for the sensor fusion to yield correct results. Moreover, it is required that the synchronized time correlates to the real time in the real world. If e.g. synchronized time and real time drift apart, sensor fusion will not yield correct results anymore.
MICROSAR Safe provides time synchronization using different communication busses like CAN, FlexRay and Ethernet. The used mechanisms for time synchronization differ between the different bus systems. This impacts the achievable accuracy of the synchronized time.
MICROSAR Safe can be used as time master and time slave.
MICROSAR Safe does not claim a synchronized state if the reported time is not synchronized to the master.
MICROSAR Safe relies on the integrity of the local clock source used for synchronization. MICROSAR Safe does not monitor the local clock source. Especially, drift and jumps are not monitored by MICROSAR Safe.
MICROSAR Safe does not detect a loss of accuracy resulting from faults in the local clock source (Ethernet) or unexpected interrupt latency (CAN and FlexRay).
- ObjectType: DocItem

### 4649b79ec5d6843939e0e0eeb76a85c80762f80baa35f155b1eaa5b7f945ad13: Assumptions of Use
- ChapterNumber: 1.4
- ObjectType: DocItem

#### b7ce8979252deb5edf0b8f75132a0378c106d23fcc50db7cb8a1c971ecb89b98: Safety Concept
- ChapterNumber: 1.4.1
- ObjectType: DocItem

##### d11949442ee770bb3120c5554c4f72a6cb4ee93bf240f5aed7d9d425d5766bd9
The user of MICROSAR Safe shall be responsible for the functional safety concept.
The overall functional safety concept is in the responsibility of the user of MICROSAR Safe. MICROSAR Safe can only provide parts that can be used to implement the functional safety concept of the item.
It is also the responsibility of the user of MICROSAR Safe to configure MICROSAR Safe as intended by the user's safety concept.
The safety concept shall only rely on safety requirements explicitly described in this safety manual. If a component from MICROSAR Safe does not explicitly describe safety requirements in this safety manual, this component has been developed according to the methods for ASIL D to provide coexistence with other ASIL components.
- Example: NvM provides safety requirements for writing and reading of data, the lower layers, i.e. MemIf, Ea, Fee and drivers, only provide the ASIL for coexistence.
The safety concept shall not rely on functionality that is not explicitly described as safety requirement in this safety manual. This functionality may fail silently in case of a detected fault.
- Example: If a potential out-of-bounds memory access, e.g. due to invalid input or misconfiguration, is detected the requested function will not be performed. An error via DET is only reported if error reporting is enabled.
Vector recommends including the components from MICROSAR Safe in the software architecture of the project.
Vector assumes that safety requirements in the user's project are mapped to the corresponding components of MICROSAR Safe.
Vector assumes that the user checked that the assumed safety requirements provided by the component of MICROSAR Safe matches the allocated safety requirement in the software architecture of the project.
- ForeignTraceId: SMI-14
- ForeignAlternativeId: SMI-4D8F1166-26BC-4920-976E-3D5ECD4E802E
- ObjectType: RQM_SAFETY_MANUAL_ITEM

##### 0e90a99e83a14c0130c72da008e62f56f755c037a3fc4011e53de86a2b864ff0
The user of MICROSAR Safe shall adequately address hardware faults.
The components of MICROSAR Safe can support in the detection and handling of some hardware faults (e.g. using watchdog).
MICROSAR Safe does not provide redundant data storage.
The user of MICROSAR Safe especially shall address faults in volatile random access memory, non-volatile memory, e.g. flash or EEPROM, and the CPU.
MICROSAR Safe relies on the adequate detection of faults in memory and the CPU by other means, e.g. hardware. Thus, Vector recommends using lock-step CPUs together with ECC memory.
See also SMI-14.
- ForeignTraceId: SMI-1
- ForeignAlternativeId: SMI-ADCDF2B9-D3DA-4952-9801-04098A0E5344
- ObjectType: RQM_SAFETY_MANUAL_ITEM

##### a34d3a909f182e4065889e4e79bf956e0bf07f912b73255b27bdfcffee6bcd0f
The user of MICROSAR Safe shall ensure that the reset or powerless state is a safe state of the system.
Vector uses this assumption in its safety analyses and development process.
- ForeignTraceId: SMI-10
- ForeignAlternativeId: SMI-BB3183AB-388F-4D50-AC7A-38CB12F1D587
- ObjectType: RQM_SAFETY_MANUAL_ITEM

##### 77e1fdf652a582de093fd626b7ff5df5beb862e879ef7f01716b6186c71b6e56
The user of MICROSAR Safe shall implement a timing monitoring using e.g. a watchdog.
The components of MICROSAR Safe do not provide mechanisms to monitor their own timing behavior.
The watchdog stack that is part of MICROSAR Safe can be used to fulfill this assumption.
If the safety concept also requires logic monitoring, the watchdog stack that is part of MICROSAR Safe can be used to implement it.
The watchdog is one way to perform timing monitoring. Today the watchdog is the most common approach. In future, there may be different approaches e.g. by monitoring using a different ECU.
The timing protection provided by the operating system can only partially replace the usage of a timing monitoring by a watchdog, because e.g. deadline violations cannot be directly detected by the OS timing protection.
See also SMI-14.
- ForeignTraceId: SMI-20
- ForeignAlternativeId: SMI-4B2F1DA2-76F2-4CB7-AE82-4850DEE70750
- ObjectType: RQM_SAFETY_MANUAL_ITEM

##### 4b2804eef6f92071a13ee2032e91b9c9e6576fabcba442885e19004edebbb0c8
The user of MICROSAR Safe shall ensure an end-to-end protection for safety-related communication between ECUs.
The communication components of MICROSAR Safe do not assume sending or receiving as a safety requirement, because considered faults can only be detected using additional information like a cycle counter. Vector always assumes that an end-to-end protection or equivalent mechanism is implemented on application level.
Considered faults in communication are:
- Failure of communication peer
- Message masquerading
- Message corruption
- Unintended message repetition
- Insertion of messages
- Re-sequencing
- Message loss
- Message delay
This requirement can be fulfilled by e.g. using the end-to-end protection wrapper for safety related communication.
- ForeignTraceId: SMI-98
- ForeignAlternativeId: SMI-014FD976-B0DF-4666-AF6F-FE28F7723A89
- ObjectType: RQM_SAFETY_MANUAL_ITEM

##### 233247128d3f0bfaedca53c8274a0553aa284b28d9585ea4cd0f1a9351b6a7e4
The user of MICROSAR Safe shall ensure data consistency for its application.
Data consistency is not automatically provided when using MICROSAR Safe. MICROSAR Safe only provides services to support enforcement of data consistency. Their application is in the responsibility of the user of MICROSAR Safe.
To ensure data consistency in an application, critical sections need to be identified and protected.
To identify critical sections in the code, e.g. review or static code analysis can be used.
To protect critical sections, e.g. the services to disable and enable interrupts provided by the MICROSAR Safe operating system can be used.
To verify correctly implemented protection, e.g. stress testing or review can be used.
Note the AUTOSAR specification with respect to nesting and sequence of calls to interrupt enabling and disabling functions.
See also TSR-101876.
- ForeignTraceId: SMI-11
- ForeignAlternativeId: SMI-9BEF83F0-3204-47A0-A0B6-FEC12FD9A990
- ObjectType: RQM_SAFETY_MANUAL_ITEM

#### 0545feb6174f9c538e0aea5ffd313c36bf4750ffc0922ed0df94b823ea120c52: Integration of MICROSAR Safe Components
- ChapterNumber: 1.4.2
- ObjectType: DocItem

##### c899d11a3e4dc5345d0fef5c41e58015eeed116592990dd14ab2f890e22d0234
The user of MICROSAR Safe shall adequately select the type definitions to reflect the hardware platform and compiler environment.
The user of MICROSAR Safe is responsible for selecting the correct platform types (PlatformTypes.h) and compiler abstraction (Compiler.h). Especially the size of the predefined types shall match the target environment.
Example: A uint32 shall be mapped to an unsigned integer type with a size of 32 bits.
The user of MICROSAR Safe can use the platform types provided by Vector. Vector has created and verified the platform types mapping according to the information provided by the user of MICROSAR Safe.
- ForeignTraceId: SMI-2
- ForeignAlternativeId: SMI-69B7C553-B9D9-4868-AFE9-ACEC1FFF2E3A
- ObjectType: RQM_SAFETY_MANUAL_ITEM

##### 3a098fd318b7d6d72bf383cbb71fcbe6d3cc73ad010331f49769bb41e9e1c62f
The user of MICROSAR Safe shall initialize all components of MICROSAR Safe prior to using them.
This constraint is required by AUTOSAR anyway. Vector uses this assumption in its safety analyses and development process.
Unintended re-initialization may lead to unintended behavior. Thus, the user shall ensure that initialization shall occur only at defined points in time.
Correct initialization can be verified, e.g. during integration testing.
- ForeignTraceId: SMI-12
- ForeignAlternativeId: SMI-1CA9D32E-C888-46C9-902C-240BE93D5966
- ObjectType: RQM_SAFETY_MANUAL_ITEM

##### 6b06c95347759a04de74d2ada1b667246ff5b99f0bc514fbf780e4a592352fb1
The user of MICROSAR Safe shall only pass valid pointers at all interfaces to MICROSAR Safe components.
Plausibility checks on pointers are performed by MICROSAR Safe (see also SMI-18), but they are limited. MICROSAR Safe components potentially use provided pointers to write to the location in memory.
Also the length and pointer of a buffer provided to a MICROSAR Safe component need to be consistent.
This requirement applies to QM as well as ASIL components. For example an NvM executed in an ASIL context will write to addresses provided by a QM software components. This requirement does not apply to interfaces between MICROSAR Safe components, because that has been verified by Vector already.
This can e.g. be verified using static code analysis tools, reviews and integration testing.
- ForeignTraceId: SMI-16
- ForeignAlternativeId: SMI-F4C69726-B6FC-478D-A378-6BADF9F6E265
- ObjectType: RQM_SAFETY_MANUAL_ITEM

##### 112d663b89dadade6d1e9970b38ea97d67cff5db7c234a7609c5543ab48c3366
The user of MICROSAR Safe shall only retain pointers provided by MICROSAR Safe where explicitly stated.
Some MICROSAR Safe components provide call-outs to user or application code. The pointers passed to these call-outs may have limited validity.
The user of MICROSAR Safe shall ensure that pointers are not used neither for reading nor for writing after returning from the call-out. Exceptions of this rule are explicitly documented for the respective call-out.
- ForeignTraceId: SMI-36039
- ForeignAlternativeId: SMI-AA0E1928-C3E2-4BA3-9832-8049DF7369B8
- ObjectType: RQM_SAFETY_MANUAL_ITEM

##### b5953d0983dd04040ced2c14adccfb86776e37b76bfcc4fbc5f7a4c0a594fd4a
The user of MICROSAR Safe shall ensure the correct usage of the provided API from MICROSAR Safe components.
The correct usage of APIs is documented in the respective Technical Reference of the component.
If a component is used incorrectly, it may not fulfill its functionality as specified. Example: If the wrong data is handed over to the communication stack, the communication stack will send this wrong data on the bus.
This requirement is only applicable if using MICROSAR Safe in a system with safety-related availability requirements.
For components of MICROSAR Safe this requirement is only fulfilled if they have the required Technical Safety Requirements assumed (please see respective section of a component if the Technical Safety Requirement is assumed by that component) and are in turn used correctly again.
- ForeignTraceId: SMI-494148
- ForeignAlternativeId: SMI-4F018A6F-AD4A-4023-944A-CC014442CBF5
- ObjectType: RQM_SAFETY_MANUAL_ITEM

##### 9317262aa7fe1561944d8534c5610a39d2ab3936e668051302ee8a7624265243
The user of MICROSAR Safe shall enable plausibility checks for the MICROSAR Safe components.
This setting is necessary to introduce defensive programming and increase robustness at the interfaces as required by ISO 26262.
This setting shall be configured at /MICROSAR/EcuC/EcucGeneral/EcuCSafeBswChecks and <Component-specific path>/<Ma>SafeBswChecks for all components that are intended to be ASIL.
Ma is the Module Abbreviation.
This setting is enforced by an MSSV plug-in.
This setting does not enable error reporting to the DET component.
- ForeignTraceId: SMI-18
- ForeignAlternativeId: SMI-68A3554E-18AF-4DE8-B9AD-169BBAD0959F
- ObjectType: RQM_SAFETY_MANUAL_ITEM

##### bf778026e12dfa5c5ca79ab52274948b05b57673d2779db084feefcf209e1f49
The user of MICROSAR Safe shall configure and use the interrupt system correctly.
The user of MICROSAR Safe is responsible for a correct and consistent configuration and usage of the interrupt system.
Especially the following topics shall be verified:
- Consistent configuration of interrupt category, level and priority in OS and MCAL modules
- Correct assignment of logical channels/instances to interrupt vectors in case of MCAL modules with multiple channels/instances
- The interrupt controller is configured in a mode which processes interrupts of the same level sequentially to avoid unbounded interrupt nesting
- ForeignTraceId: SMI-1725
- ForeignAlternativeId: SMI-740BC552-4548-4480-A726-0A5B02030204
- ObjectType: RQM_SAFETY_MANUAL_ITEM

##### 0bf75a192260f939c177225637f4b2e1552e5f7825f7e6d5c31165ee1a31c1be
The user of MICROSAR Safe shall not use functionality of MICROSAR Safe components marked with a BETA-ESCAN.
Functionality marked with a BETA-ESCAN is not thoroughly tested by Vector.
Vector ensures that functionality marked with a BETA-ESCAN can be completely disabled.
The list of ESCANs (incl. BETA-ESCANs) is provided with a delivery.
- ForeignTraceId: SMI-36041
- ForeignAlternativeId: SMI-A887D9FE-E9EC-4E84-B3A4-A61C31959CA1
- ObjectType: RQM_SAFETY_MANUAL_ITEM

#### 5b7b5b30b05ab19b0946047ed8f2f0dd8006e50e55b04be8a82f7319c832819b: Partitioning
- ChapterNumber: 1.4.3
- ObjectType: DocItem

##### fa08dda52b944469881f7d9f635904a7f567ad58f067d27c346a55104e5203ca
The user of MICROSAR Safe shall ensure that for one AUTOSAR functional cluster (e.g. System Services, Operating System, CAN, COM, etc.) only components from Vector are used.
This assumption is required because of dependencies within the development process of Vector.
This assumption does not apply to the MCAL or the EXT cluster.
Vector may have requirements on MCAL or EXT components depending on the upper layers that are used and provided by Vector. For example, the watchdog driver is considered to have safety requirements allocated to its initialization and triggering services. Details are described in the component specific parts of this safety manual.
This assumption does not apply to components that are not provided by Vector at all.
In case the partitioning solution is used, this assumption only partially applies to the System Services cluster. Only the Watchdog Manager and Watchdog Interface need to be used from Vector then, because the Watchdog Manager and Watchdog Interface will be placed in separate memory partitions apart from the other System Services components.
- ForeignTraceId: SMI-9
- ForeignAlternativeId: SMI-C34BDDBC-8A15-49DE-96C6-BEBB883083CF
- ObjectType: RQM_SAFETY_MANUAL_ITEM

##### e1d54c4403b05db148862bd5421dd5a57622bfd534a3a1d7919f2add49c55db9
<Unparsable text>
- ForeignTraceId: SMI-32
- ForeignAlternativeId: SMI-B3CAEF5A-5B13-474E-B97A-7AA6EFB4D9FB
- ObjectType: RQM_SAFETY_MANUAL_ITEM

##### 3750cb93cf59cc79023cad61992304518708e6bb511ce38a503883b0a5ebaa20
The user of MICROSAR Safe shall verify that the memory mapping is consistent with the partitioning concept.
The volatile data of every component shall be placed in the associated memory partition. This can be verified e.g. by review of the linker map file.
The memory sections for each component placed in RAM can be identified <MIP>_START_SEC_VAR[_<xxx>], where <MIP> is the Module Implementation Prefix of the component.
It is assumed that the MPU is configured to not allow write access by a partition with lower integrity to data from a partition with higher integrity.
- ForeignTraceId: SMI-99
- ForeignAlternativeId: SMI-E89CCE42-2897-4566-9A09-4133E1568B4B
- ObjectType: RQM_SAFETY_MANUAL_ITEM

#### ec2bafd8c33f9452dd62d0da3121cc8f155ecedd02729979a94b5859858ba0d0: Resources
- ChapterNumber: 1.4.4
- ObjectType: DocItem

##### f5509e2877362953edddf65dbb1001d71f03d1b74903205a458fb6c368de82c9
The user of MICROSAR Safe shall provide sufficient resources in RAM, ROM, stack and CPU runtime for MICROSAR Safe.
Selection of the microcontroller and memory capacities as well as dimensioning of the stacks is in the responsibility of the user of MICROSAR Safe.
If MICROSAR Safe components have specific requirements, these are documented in the respective Technical Reference document.
- ForeignTraceId: SMI-33
- ForeignAlternativeId: SMI-7664C682-8A77-499B-A497-3EA3DB39D0D4
- ObjectType: RQM_SAFETY_MANUAL_ITEM

##### 220bee67e6331e1e4aa9a3c8322c4f0b90b4db4b24e2d100acd96d3edbd1a10d
The user of MICROSAR Safe shall perform a worst-case execution time analysis when using MICROSAR Safe in systems with safety-related availability requirements.
In systems with safety-related availability requirements, it is assumed that an upper bound for the execution time of MICROSAR functionality is required.
This requirement is only applicable if using MICROSAR Safe in a system with safety-related availability requirements.
- ForeignTraceId: SMI-246328
- ForeignAlternativeId: SMI-6EBF6C81-8C28-4A0D-9B04-6E37CAD95406
- ObjectType: RQM_SAFETY_MANUAL_ITEM

#### 38839aab5c81957403cfe860f4257f68c6e2e65d19d6c128c4341634e84689c4: Process
- ChapterNumber: 1.4.5
- ObjectType: DocItem

##### 7fe12ed8ec6348d79afce9c36079f123e99d134955b5df9acf207056036db6a6
The user of MICROSAR Safe shall follow the instructions of the corresponding Technical Reference of the components.
Especially deviations from AUTOSAR specifications are described in the Technical References.
If there are constraints for the implementation of an exclusive area, these are described in the Technical References.
- ForeignTraceId: SMI-15
- ForeignAlternativeId: SMI-877A9D63-DAF2-4B2F-B01F-D7107E7BF399
- ObjectType: RQM_SAFETY_MANUAL_ITEM

##### ccb7d53647a8a5536e8cab50a05c0c1f1d7b3a13dfc1cad56417ae27a8d1aca6
The user of MICROSAR Safe shall verify all code that is modified during integration of MICROSAR Safe.
Code that is typically modified by the user of MICROSAR Safe during integration comprises generated templates, hooks, callouts, or similar.
This assumption also applies if interfaces between components are looped through user-defined functions.
Vector assumes that this verification also covers ISO 26262:6-9. Vector assumes that modified code that belongs to a Vector component, e.g. EcuM callouts or OS trace hooks can at least coexist with this component, because no separation in memory or time is implemented.
Example: Callouts of the EcuM are executed in the context of the EcuM.
Non-trusted functions provided by the Vector operating system can be used to implement a separation in memory in code modified by the user of MICROSAR Safe.
- ForeignTraceId: SMI-5
- ForeignAlternativeId: SMI-7519BE87-DB0A-4ED3-A148-CCA75D43FA27
- ObjectType: RQM_SAFETY_MANUAL_ITEM

##### d7d157bcfe3c17e743e556104366952aa8d33de857dd58c08059564d51aec5e8
The user of MICROSAR Safe shall only modify source code of MICROSAR Safe that is explicitly allowed to be changed.
Usually no source code of MICROSAR Safe is allowed to be changed by the user of MICROSAR Safe.
The user of MICROSAR Safe can check if the source code was modified by e.g, comparing it to the original delivery.
- ForeignTraceId: SMI-30
- ForeignAlternativeId: SMI-E4104504-709A-45AC-8889-544F1478A78D
- ObjectType: RQM_SAFETY_MANUAL_ITEM

##### ea05d9ab7d2e9123dc3715c1ccb894c8dc4fa0b1feb9a0c7722e5a7dd2019eef
The user of MICROSAR Safe shall verify generated functions according to ISO 26262:6-9.
Generated functions can be identified when searching through the generated code.
An example of generated functions is the configured rules of the Basic Software Manager (BswM). Their correctness can only be verified by the user of MICROSAR Safe. Please note, however, that BswM not necessarily assumes a safety requirement.
This requirement does not apply to MICROSAR SafeRTE and the transformers (ComXf, DiagXf, E2eXf, SomeIpXf).
- ForeignTraceId: SMI-8
- ForeignAlternativeId: SMI-71AAAA1B-FCA6-46CC-8DF0-D1756A1C20B5
- ObjectType: RQM_SAFETY_MANUAL_ITEM

##### b6e245ce018b22d7067197a70034895fd21fadfc44b425b2eaf443e67021fd41
The user of MICROSAR Safe shall execute the MICROSAR Safe Silence Verifier (MSSV).
MSSV is used to detect potential out-of-bounds accesses by Vector's basic software based on inconsistent configuration.
Details on the required command line arguments and integration into the tool chain can be found in [4].
If the report shows “Overall Check Result: Fail", please contact Vector.
- ForeignTraceId: SMI-19
- ForeignAlternativeId: SMI-C9E8EA37-6C92-4D56-AA5A-98A17FD0AA11
- ObjectType: RQM_SAFETY_MANUAL_ITEM

##### 440907830032703fdae5b80d6b9769737b032d27eb79fe43796f8a3930606bfe
The user of MICROSAR Safe shall execute the Vector Code Analyzer (VCA).
The Vector Code Analyzer is used to detect potential out-of-bounds accesses by Vector's basic software.
This requirement only applies if the Vector Code Analyzer is delivered.
Details on the required command line arguments and integration into the tool chain can be found in [5].
If the report shows “Overall Check Result: Fail", please contact Vector.
- ForeignTraceId: SMI-428133
- ForeignAlternativeId: SMI-761BF9D8-54FA-4BE8-BB6A-07296C16D10C
- ObjectType: RQM_SAFETY_MANUAL_ITEM

##### e9dd7dfd407a3242165974c8a8f2becc4c421a2b6aa8ddad8e36d18c0aa0c883
The user of MICROSAR Safe shall perform the integration (ISO 26262:6-10) and verification (ISO 26262:6-11) processes as required by ISO 26262.
Especially, the safety mechanisms and safety-related functionality shall be verified in the final target ECU.
As a prerequisite, Vector assumes that the safety concept by the user of MICROSAR Safe allocates safety requirements to the individual components of MICROSAR Safe (see SMI-14).
Vector assumes that by performing the integration and verification processes as required by ISO 26262 the generated configuration data, e.g. data tables, task priorities or PDU handles, are sufficiently checked. An additional review of the configuration data is then considered not necessary.
Integration does not apply to a MICROSAR Safe component that consists of several units. This integration is already performed by Vector.
However, integration of all MICROSAR Safe components in the specific use-case of the user of MICROSAR Safe is the responsibility of the user of MICROSAR Safe. This also includes the hardware-software integration in the context of the target ECU.
Vector assumes that the integration test performed by the user fulfills the exit criteria defined by ISO 26262:6-10 (Structural coverage at the software architectural level) and ISO 26262:6-11.
Vector assumes that in corresponce with the required ASIL for the project of the user of MICROSAR Safe, typical tests methods, like equivalence classes and boundary value analysis are applied. Creating equivalence classes might reduce testing effort with respect to testing all individual instances of a test object.
Vector especially assumes that in correspondence with the required ASIL for the project of the user of MICROSAR Safe, safety mechanisms are tested using fault injection. Example: Restbus simulation of relevant E2E faults for protected signal groups.
- ForeignTraceId: SMI-4
- ForeignAlternativeId: SMI-907DB2EC-1621-4052-91B3-316CC9C798E7
- ObjectType: RQM_SAFETY_MANUAL_ITEM

##### 1368d5dd9ffca3bb4a27adca6cf252913c6dde6124bf6e5c9f4775678fb3bf11
The user of MICROSAR Safe shall ensure that a consistent set of generated configuration is used for verification and production.
Make sure that the same generated files are used for testing and production code. E.g. be aware that configuration can be changed in the DaVinci tools without generating the code again.
Make sure that all generated files have the same configuration basis, i.e. always generate the MICROSAR Safe configuration for all components for a relevant release of the ECU software.
The use of post build loadable is supported but not recommended by Vector. Post build loadable increases complexity of verification and validation processes due to increased number of variants. There is no support by Vector to qualify the post build loadable tool chain provided by Vector to create binary data without a qualified compiler.
- ForeignTraceId: SMI-100
- ForeignAlternativeId: SMI-A1261C5F-41C1-4DE2-910F-3A1FC76E5362
- ObjectType: RQM_SAFETY_MANUAL_ITEM

##### 047069bc31b359b881a1c4c8bfa24a909798588113feead48f469d9e35547276
The user of MICROSAR Safe shall verify the integrity of the delivery by Vector.
Run the SIPModificationChecker.exe and verify that the source code, BSWMD and safety manual files are unchanged.
- ForeignTraceId: SMI-176
- ForeignAlternativeId: SMI-E5CE274D-E46F-46B1-AF52-59BA1CF8A38C
- ObjectType: RQM_SAFETY_MANUAL_ITEM

##### 84deccd093b5c1b3e6109b3a8d18e3a585d52a284414eb9307d93000c57d7127
The user of MICROSAR Safe shall verify the consistency of the binary downloaded into the ECU's flash memory.
This also includes re-programming of flash memory via a diagnostics service. The consistency of the downloaded binary can be checked by the bootloader or the application. MICROSAR Safe assumes a correct program image.
- ForeignTraceId: SMI-31
- ForeignAlternativeId: SMI-D3F2CD03-D9A0-407D-863C-DC275B6427E8
- ObjectType: RQM_SAFETY_MANUAL_ITEM

##### 51da3efffb2357686dbaf60f3d22142595c875b6eac858d19c7af723a96c6530
The user of MICROSAR Safe shall evaluate all tools (incl. compiler) that are used by the user of MICROSAR Safe according to ISO 26262:8-11.
Evaluation especially shall be performed for the compiler, linker, debugging and test tools.
Vector provides a guideline for the evaluation of the Tool Confidence Level (TCL) for the tools provided by Vector (e.g. DaVinci Configurator PRO).
MSSV and RTE Analyzer can be assumed TCL2 and qualified for this TCL, since a safety-related development process at Vector is applied for those tools. Confirmation that this safety-related development process was applied is part of the safety case.
Vector has only evaluated the tools used by Vector during the development of MICROSAR Safe. Tool evaluation, for tools used by the user of MICROSAR Safe, is in the responsibility of the user of MICROSAR Safe.
- ForeignTraceId: SMI-3
- ForeignAlternativeId: SMI-0E3D106A-786E-4A31-8641-0027982251AF
- ObjectType: RQM_SAFETY_MANUAL_ITEM

## 75113519ab0cd313b8812874a0f95d8efeb8a40b0046e69831a429cd41bd4ee7: Safety Manual ComXf
- ChapterNumber: 2
- ObjectType: DocItem

### fdcd847e540bf782faebf676f63c94a0540d227fd6895f9a0f649c7370799fe4: Assumed safety requirements
- ChapterNumber: 2.1
- ObjectType: DocItem

#### 58ef9ce3cb06e14b555ec93a364b8ea1972b1f6754f382fc68a81b61d9a4f82b
This component assumes the following safety requirements:
| ID | Safety Requirement | Associated TSR | ASIL |
| --- | --- | --- | --- |
| CREQ-108114 | ComXf shall provide a service to initialize itself. | TSR-1 | ASIL D |
| CREQ-108117 | ComXf shall provide a service to transform a Sender/Receiver communication. | TSR-10,TSR-111108 | ASIL D |
| CREQ-108118 | ComXf shall provide a service to retransform a Sender/Receiver communication. | TSR-10,TSR-111108 | ASIL D |
This component in addition to the assumed safety requirements ensures freedom from interference with respect to memory (and timing) with up to ASIL D.
- ForeignTraceId: SMI-62930
- ForeignAlternativeId: SMI-B2255906-E38C-4907-B9FC-54A52B637047
- ObjectType: RQM_SAFETY_MANUAL_ITEM

### dd9ec4e5c2e0579bcce1dd28f2ee2c8e2395d729963e77fc47054d7f019ea215: Configuration constraints
- ChapterNumber: 2.2
- ObjectType: DocItem

#### c26cf596236680a9ccb0ccc99d4340adbf73addb9ce58abef7e476d9ff2182b1
This component does not have configuration constraints.
- ObjectType: DocItem

### 15cdce24d41d1c2c6646d0a374b760c5c234e437625fecd15973b0a9d6cb95e5: Additional verification measures
- ChapterNumber: 2.3
- ObjectType: DocItem

#### 6aa88d01812921e4a1e29f6f7af2ea5aace7b08b415bb315754e8c670470e35f
Please note that the ComXf Generator and RTE Analyzer only implement measures to detect systematic faults by the software. No measures are implemented to detect or mitigate random faults on the computer used for generation.
- ObjectType: DocItem

#### 045d2535e6be7f1fa09404623b79c7cb0e61b84bdbcb955a2357b2d0a28f392c
The user of MICROSAR Safe shall execute the RTE Analyzer.
The RTE Analyzer performs checks to identify faults in ComXf. Especially out-of-bounds accesses within ComXf are detected. If RTE Analyzer reports a fault, the generated ComXf cannot be used. Moreover it provides the user of MICROSAR Safe with feedback what was generated. This feedback shall be reviewed during integration testing against the intended software design and its configuration.
Please see the Technical Reference of the RTE Analyzer how to execute it.
- ForeignTraceId: SMI-62929
- ForeignAlternativeId: SMI-BFC1E099-F9D1-49D0-A605-96C76FEB819C
- ObjectType: RQM_SAFETY_MANUAL_ITEM

#### b32f76d5365c785ae5dc68c45fb64cd03392d4f488ea7f8c9a653c26a2784c59
The user of MICROSAR Safe shall ensure that the RTE Analyzer does not report unsupported templates.
The generated ComXf code is based on templates. The templates are instantiated by the ComXf Generator in different variants. The RTE Analyzer verifies that the analyzed template variants have been tested during the development of the ComXf Generator according to ISO 26262.
The last section of the RTE Analyzer configuration feedback report provides the information about the template variants.
The report must show that no unsupported templates have been found.
- ForeignTraceId: SMI-62931
- ForeignAlternativeId: SMI-AAA5E5C0-3385-48ED-90A2-8B267FD78004
- ObjectType: RQM_SAFETY_MANUAL_ITEM

#### c6305ee051a051638b50048d2c9852cf6a4c12e899b492e034ff9095afd4bdfe: Guided integration testing
- ChapterNumber: 2.3.1
- ObjectType: DocItem

##### 0f31cf33b295a7f9fd23602a688392e7a08a711bcbb67a5f962181bd8ba22b8d
Residual faults in the ComXf Generator can only be found during integration testing. Vector assumes that the user of MICROSAR Safe performs an integration testing and verification of software safety requirements according to ISO 26262 Part 6 Clauses 10 and 11 (see also SMI-4). To support this integration testing the RTE Analyzer produces a configuration feedback report.
Please refer to the Technical Reference of the RTE Analyzer for a description of the configuration feedback report.
The following subsections describe the requirements that must be fulfilled during integration testing and verification of software safety requirements.
Each Safety Manual Item (SMI) is structured in the following way:
- The requirement that must be fulfilled
- Explanation of the requirement and a rationale
- Recommended configuration constraints (optional)
- Recommended means of complying with the requirement (optional)
- Details on the information provided by the RTE Analyzer supporting this requirement
- ObjectType: DocItem

##### 7b0b7c6e76a9ca9eb4a518e0e8a1d8737f5204712f9e4c22c32f34ed42a2a69c
The user of MICROSAR Safe shall ensure that ComXf serializes and deserializes the data in the format that is expected by the network.
Inconsistencies in the communication extract, the configuration of the communication stack, the ComXf configuration and the RTE configuration can lead to missinterpretation of signal group data.
This requires verification of:
- data type
- bit position
- endianess
- length
for every group signal.
Vector requires using E2E protection for safety-related signals.
Verification of the serialization can e.g. be performed by integration testing on vehicle network level with minimum and maximum values for every group signal.
Example:
For a unsigned 3-bit group signal the values 0 and 7 specify the lower and upper limit.
For a signed 3-bit group signal the values -4 and 3 specify the lower and upper limit.
The RTE Analyzer lists the APIs of SWCs that use ComXf to assist in this integration step.
The ComXf API names contain the signal group names.
- ForeignTraceId: SMI-62933
- ForeignAlternativeId: SMI-A6B809E3-501F-4C39-9DBF-F949700B3385
- ObjectType: RQM_SAFETY_MANUAL_ITEM

### f65d5bf06eff638d9269d2469349b16885a585b315a6f6aae132b9a0c11f83a8: Safety requirements required from other components
- ChapterNumber: 2.4
- ObjectType: DocItem

#### d896023bb953970a4339a40b750f22440e6ad346a4b5c64d889490cb87285365
COMXF requires the following functionality as safety requirements from the RTE:
- Transformer handling (TSR-10)
For components provided as part of MICROSAR Safe, the respective section of the Safety Manual for that component allows you identifying if this requirement is fulfilled.
- ForeignTraceId: SMI-857104
- ForeignAlternativeId: SMI-BCD88787-0357-4D6C-A0BF-01A0CCF3B9E0
- ObjectType: RQM_SAFETY_MANUAL_ITEM

### e615df7351a81d514eec1df8fb49c6525a362ebdd5eff9471c6ad8926748b70a: Dependencies to hardware
- ChapterNumber: 2.5
- ObjectType: DocItem

#### 1bf91416610c34669610f3c8d22760440280096ef35e364cb4df31cff5fec5cc
This component does not use a direct hardware interface.
- ObjectType: DocItem

## 7b3683ef24147faf18aaaf3e649273b8741d00942b70fe887b8cec607e3e80a3: Safety Manual Crc
- ChapterNumber: 3
- ObjectType: DocItem

### 32555d3d753429f68897e1825029c22c6262068a80cd4c43a2ae03a30db84bf5: Assumed safety requirements
- ChapterNumber: 3.1
- ObjectType: DocItem

#### 71fba7f601d2644add34786672ad563b9e0702d6a6398b42771fbd8fb94c5e35
This component assumes the following safety requirements:
| ID | Safety Requirement | Associated TSR | ASIL |
| --- | --- | --- | --- |
| CREQ-858 | Crc shall provide a service to calculate 8-bit SAE-J1850 CRC. | TSR-10 | ASIL D |
| CREQ-859 | Crc shall provide a service to calculate 8-bit 0x2F CRC. | TSR-10 | ASIL D |
| CREQ-860 | Crc shall provide a service to calculate 16-bit CCITT CRC. | TSR-10 | ASIL D |
| CREQ-861 | Crc shall provide a service to calculate 32-bit IEEE-802.3 CRC. | TSR-10 | ASIL D |
| CREQ-862 | Crc shall provide a service to calculate 32-bit E2E Profile 4 CRC. | TSR-10 | ASIL D |
| CREQ-117997 | Crc shall provide a service to calculate 64-bit ECMA CRC. | TSR-10 | ASIL D |
This component in addition to the assumed safety requirements ensures freedom from interference with respect to memory with up to ASIL D.
- ForeignTraceId: SMI-344
- ForeignAlternativeId: SMI-74A4C01B-B6C8-4566-A8FE-CBF8DB13ED36
- ObjectType: RQM_SAFETY_MANUAL_ITEM

#### a73325e09bece79ce209fb7c5523263050a62482377e697dec0789d4f7aa7c69
This component in addition to the assumed safety requirements ensures freedom from interference with respect to memory with up to ASIL D.
- ObjectType: DocItem

### 74195ecdb963cac8541274ab33f8b4299aeb9a99cd867b586847d51c8a86570f: Configuration constraints
- ChapterNumber: 3.2
- ObjectType: DocItem

#### 93ea045153d11810b1a475b61a355d23c48ed9f5bccbf882672877662eb4d396
This component does not have configuration constraints.
- ObjectType: DocItem

### f02ab7d5782806f936f3b931bda61544d74593cdeb21d1439d72478862e0b7db: Additional verification measures
- ChapterNumber: 3.3
- ObjectType: DocItem

#### 0cdd3a53d7583fbdb226eaea95cc24ed8b84ea37fcd78025813baf4589e664e2
The user of MICROSAR Safe shall verify that the CRC is calculated for the intended data.
This includes the intended buffer and its size (see also SMI-16), start value and if it is the first call to the service.
Verification can be performed by the "magic check" (see AUTOSAR SWS Crc).
If Crc is used by a MICROSAR Safe component (e.g. E2E, NvM), this requirement is fulfilled for the MICROSAR Safe component.
- ForeignTraceId: SMI-49
- ForeignAlternativeId: SMI-62FE1B77-BBCF-4D73-A380-A11F7BAFD5B8
- ObjectType: RQM_SAFETY_MANUAL_ITEM

### 42fec7083c310b1de7208ab69fe68b797f69666ec3d2c5662c629cb29aa7963d: Safety requirements required from other components
- ChapterNumber: 3.4
- ObjectType: DocItem

#### 6246dda56d448d84125e35cf2359680a4871ab62742385df1dc4fc1226c1c079
This component has no safety requirements from other components.
- ObjectType: DocItem

### 80f3a0cac526797d1556d4d10d14b29d57a3f4621cbdf590f4ec7ea05fa7124c: Dependencies to hardware
- ChapterNumber: 3.5
- ObjectType: DocItem

#### d2e699137fb4b2d39d04b39b539f26a10dfde6051dd33407501e8d2fb4b3af9b
This component does not use a direct hardware interface.
- ObjectType: DocItem

## d469aa73b64f05ea60234a004e9a340be16621b2de762de779892cc6900be1a8: Safety Manual DiagXf
- ChapterNumber: 4
- ObjectType: DocItem

### f700f94f4576f9a60c86facec386efe90dcda0dfeda4b7ea1d32109824543d6f: Assumed safety requirements
- ChapterNumber: 4.1
- ObjectType: DocItem

#### 72fbceab3096472aa11757c943ee97719f2e49688713363ab8e85bb534bf20c4
This component does not assume safety requirements. This component is developed according to ISO 26262 only to ensure freedom from interference with respect to memory (and timing) with up to ASIL D.
- ObjectType: DocItem

### 65b4d0249b26c55fff52d0d6b3fe40bbc714be28fae5aa8c33b5cd31344f281d: Configuration constraints
- ChapterNumber: 4.2
- ObjectType: DocItem

#### 5ee8a661864d0ee982289683c2f3cd0edde50b744e9213fb13783ffcf6dd4bd7
This component does not have configuration constraints.
- ObjectType: DocItem

### 6ceacab61adf0f866ca6c6ab238002edf09e6d28eea260f70a17af335596e3db: Additional verification measures
- ChapterNumber: 4.3
- ObjectType: DocItem

#### 642c7d4b1c9532b45b94905924ab62702817c1b47627ded45cf09bbefcc49f19
The user of MICROSAR Safe shall execute the RTE Analyzer.
The RTE Analyzer performs checks to identify faults in DiagXf. Especially out-of-bounds accesses within DiagXf are detected. If RTE Analyzer reports a fault, the generated DiagXf cannot be used. Moreover it provides the user of MICROSAR Safe with feedback what was generated. This feedback shall be reviewed during integration testing against the intended software design and its configuration.
Please see the Technical Reference of the RTE Analyzer how to execute it.
- ForeignTraceId: SMI-105504
- ForeignAlternativeId: SMI-0E3F31C7-502B-4A6E-8352-3FCAD640B1A4
- ObjectType: RQM_SAFETY_MANUAL_ITEM

#### 65c01dce63aa13436effc0665d30b272737c6102e37ccf885006d4d0fbe0f3d9
The user of MICROSAR Safe shall ensure that the RTE Analyzer does not report unsupported templates.
The generated DiagXf code is based on templates. The templates are instantiated by the DiagXf Generator in different variants. The RTE Analyzer verifies that the analyzed template variants have been tested during the development of the DiagXf Generator according to ISO 26262.
The last section of the RTE Analyzer configuration feedback report provides the information about the template variants.
The report must show that no unsupported templates have been found.
- ForeignTraceId: SMI-105505
- ForeignAlternativeId: SMI-4F957D2A-3309-403C-8AEE-15F02ED21F35
- ObjectType: RQM_SAFETY_MANUAL_ITEM

#### 3b0ebee775d18a571fc05d70dbe60b6321491867a7f02c82d4fc08348c8333f0: Guided integration testing
- ChapterNumber: 4.3.1
- ObjectType: DocItem

##### f75714542ddb53b454f3e48418ba21d958d172dc5eb465090574cfee2a604e0a
Residual faults in the DiagXf Generator can only be found during integration testing. Vector assumes that the user of MICROSAR Safe performs an integration testing and verification of software safety requirements according to ISO 26262 Part 6 Clauses 10 and 11 (see also SMI-4). To support this integration testing the RTE Analyzer produces a configuration feedback report.
Please refer to the Technical Reference of the RTE Analyzer for a description of the configuration feedback report.
The following subsections describe the requirements that must be fulfilled during integration testing and verification of software safety requirements.
Each Safety Manual Item (SMI) is structured in the following way:
- The requirement that must be fulfilled
- Explanation of the requirement and a rationale
- Recommended configuration constraints (optional)
- Recommended means of complying with the requirement (optional)
- Details on the information provided by the RTE Analyzer supporting this requirement
- ObjectType: DocItem

##### 32f8888077ce94566decfa444a4d444792321e9db72506e5f5ea2b9e08d6dbb6
The user of MICROSAR Safe shall ensure that DiagXf serializes and deserializes the data in the format that is expected by the DCM.
Inconsistencies in the diagnostic extract, the configuration of the communication stack, the DiagXf configuration and the RTE configuration can lead to missinterpretation of record data element data.
This requires verification of:
- data type
- bit position
- endianess
- length
for every record element.
Verification of the serialization can e.g. be performed by integration testing on ECU level with minimum and maximum values for every record element.
Example:
For a unsigned 3-bit record element the values 0 and 7 specify the lower and upper limit.
For a signed 3-bit record element the values -4 and 3 specify the lower and upper limit.
The RTE Analyzer lists the APIs of SWCs that use DiagXf to assist in this integration step.
The DiagXf API names contain the SWC, port and data element names.
- ForeignTraceId: SMI-105506
- ForeignAlternativeId: SMI-1CEFF17D-226A-477C-9A86-A35A82BAF7CD
- ObjectType: RQM_SAFETY_MANUAL_ITEM

### 59634508cf889ca825f992bc8f94e8971dc68de8a58d9f9bcc3b9f5c70b9c6e6: Safety requirements required from other components
- ChapterNumber: 4.4
- ObjectType: DocItem

#### e86b4b996a670c8ee6cae38df54f1528a772c114de7f88281e0576ce6ee63be3
This component does not require safety requirements from other components.
- ObjectType: DocItem

### be720cfed106a757e2a08c646d4441c0a9565bd923728306945113e08b2f7291: Dependencies to hardware
- ChapterNumber: 4.5
- ObjectType: DocItem

#### f4a6ec694a35745a89d6afc25cfccbc3adbbf6107efbaf3abd62477b51d31295
This component does not use a direct hardware interface.
- ObjectType: DocItem

## 797b3a22f1813983ca364c4be666237478c2fe1a282e8fbe5a19e10eab39224d: Safety Manual E2E
- ChapterNumber: 5
- ObjectType: DocItem

### 4866318a51631894484be18e07dd3ddbbbeaf7e0697233fefa0512b9fee3e31a: Assumed safety requirements
- ChapterNumber: 5.1
- ObjectType: DocItem

#### 365aea0e7471f03bdc7436855e851a70a049efa18830a31c5dc03413a84f4246
This component assumes the following safety requirements:
| ID | Safety Requirement | Associated TSR | ASIL |
| --- | --- | --- | --- |
| CREQ-1086 | E2E shall provide services to protect data. | TSR-10 | ASIL D |
| CREQ-1087 | E2E shall provide services to initialize the protection state. | TSR-1, TSR-10 | ASIL D |
| CREQ-1088 | E2E shall provide services to check protected data. | TSR-10 | ASIL D |
| CREQ-1089 | E2E shall provide services to initialize the check state. | TSR-1, TSR-10 | ASIL D |
| CREQ-1175 | E2E shall provide a service to map the check result to an adequate state machine status | TSR-10 | ASIL D |
| CREQ-1091 | E2E shall provide a service to check data within a reception window. | TSR-10 | ASIL D |
| CREQ-1092 | E2E shall provide a service to initialize the state machine. | TSR-1, TSR-10 | ASIL D |
- ForeignTraceId: SMI-51
- ForeignAlternativeId: SMI-78469216-9314-4CC0-B4B3-97E02FAF487C
- ObjectType: RQM_SAFETY_MANUAL_ITEM

#### 33ebcfc2cef8911fb99606d4f9c71118f796b489670fc3b40cb70bed1a0d8aa7
This component in addition to the assumed safety requirements ensures freedom from interference with respect to memory with up to ASIL D.
- ObjectType: DocItem

### e00a2e9f6130d7211f205dc33721bc27185732ed12de0eb7394f89315b56e87b: Configuration constraints
- ChapterNumber: 5.2
- ObjectType: DocItem

#### 7b6e446c674265bfc73accf14eb6047043a212043fbd1cfe6f631bb677a186ba
This component does not have configuration constraints.
- ObjectType: DocItem

### 235140972814fafe65aa7a1e5d57b8e760bffa33cdd02c36581c9f67534d786a: Additional verification measures
- ChapterNumber: 5.3
- ObjectType: DocItem

#### f79d5e73deebe683c9185bb3371db47d88d5d5ad8f996234153dcd2697d67b6f
The user of MICROSAR Safe shall verify that the E2E is used as intended.
This includes the verification of the parameters for end-to-end protection, e.g. data ID, and the order of calls as described in the Technical Reference for creating and checking the end-to-end protection.
The service to protect shall be called exactly once before sending. The service to check shall be called exactly once for reception.
This requirement is fulfilled for the MICROSAR Safe E2E Protection Wrapper and MICROSAR Safe E2E Transformer if used as specified in their respective safety manual section.
- ForeignTraceId: SMI-52
- ForeignAlternativeId: SMI-C7ED5882-17A7-40B7-92CC-1D2C214A61BB
- ObjectType: RQM_SAFETY_MANUAL_ITEM

### 4559276403bee31976df34ed526b3a440e9f49d27f9eee494d9f26dac11e00a8: Safety requirements required from other components
- ChapterNumber: 5.4
- ObjectType: DocItem

#### 8f70b3c76fa7599a75b27fdfa721c1e3e743a5abdc74b1dc2ad99ab3aec354f6
This component requires the CRC calculation functionality as an assumed safety requirement (TSR-10) from CRC component.
For components provided as part of MICROSAR Safe, the respective section of the Safety Manual for that component allows you to identify if this requirement is fulfilled.
- ForeignTraceId: SMI-50
- ForeignAlternativeId: SMI-2F4EDBAB-EAE4-4EF8-8526-F300627571C4
- ObjectType: RQM_SAFETY_MANUAL_ITEM

### cdf8e9d6e31172886a73700a6b5b82703374d2457e5656c6bc75ce632ddd3c97: Dependencies to hardware
- ChapterNumber: 5.5
- ObjectType: DocItem

#### 1bc2f3c2dec35f61dae1c61d3958711d71ceec4a1a27f145105e8fd8c7f392ea
This component does not use a direct hardware interface.
- ObjectType: DocItem

## 4175d5e873ad0048bdd107c0eadce58451990494c04a0e9b44a4f55329f2b1b6: Safety Manual E2E Protection Wrapper
- ChapterNumber: 6
- ObjectType: DocItem

### cd71b05a6d6abb7d99284150af4e574a872b6b25fb3390251bc39405e949851d
| Term/Abbreviation | Definition |
| --- | --- |
| E2EConfig | E2E Protection Wrapper configuration file. The E2EConfig file is a data file containing information about the protected areas within I-PDUs of a given AUTOSAR system that are to be protected by the E2Elib and the E2EPW and how they are to be protected. It serves as input for the E2EPWG. |
| E2EPWG | E2E Protection Wrapper Generator. It takes an E2EConfig file as input and generates the E2E Protection Wraper code. |
| node | node name (also SWC) |
| port or p | port |
| pde or o | protected data element (PDE) |
| direc | direction for which a PDE-type is configured (rx or tx) |
The shortcuts p and o are used for the E2EPW API functions. For other identifiers (like filenames) the notation port and pde is preferred.
Some identifiers in this document include concatenations of these terms.
E.g., E2EPW_Write_p_o_direc () (i.e., ".. for a combination of some port p, some data element o and some direction direc).
A protected area (PA) is the container of configuration data for a certain protected data element (PDE).
- ObjectType: DocItem

### 31b6d9a58384b78156c4b45534f07f80765609684b640d31beeeffd4153ef5b7: Safety features
- ChapterNumber: 6.1
- ObjectType: DocItem

#### f869527f2305a9d0c254f3985ec6f05ec5cb0d6b4b65548d0c2368e137f4c4f2
This component provides the following safety features:
- Creation of end-to-end protection for data
- Check of end-to-end protection for data
- ForeignTraceId: SMI-143
- ForeignAlternativeId: SMI-85174E70-1CF8-4F7A-BEBE-81EBD8ADDEBF
- ObjectType: RQM_SAFETY_MANUAL_ITEM

### c099a1c5d6d341848c2745e5242dc6d3bdc4d92fc345893b5490fbe9d9af28c6: Configuration constraints
- ChapterNumber: 6.2
- ObjectType: DocItem

#### 4a9fa047117a5df25fed86f2650a1a2ea56d0c9d22b60574d10fbf3613cd816a
The user of MICROSAR Safe shall correctly select and configure I-PDUs and their signal groups (protected areas) that are to be protected by the end-to-end protection. That is, the selection and configuration shall be made according to the communication safety requirements of the system. This includes also the selection of the E2E profile.
- ForeignTraceId: SMI-124
- ForeignAlternativeId: SMI-9748395D-778A-45E7-A772-A711F7DA70D3
- ObjectType: RQM_SAFETY_MANUAL_ITEM

#### 98951a66fe8c0918a7a5d4e119334fe85c33a6bbfdf6415d16fd30c7d05afb2b
The user of MICROSAR Safe shall only configure PAs for the same ECU in one E2EConfig.
If source code needs to be generated for different ECUs, then an individual E2EConfig file must be defined for each ECU.
- ForeignTraceId: SMI-125
- ForeignAlternativeId: SMI-9D8F79E9-9DF6-443C-9918-D9BAA120E2B2
- ObjectType: RQM_SAFETY_MANUAL_ITEM

### 85738e52bb2d9222d1a48406cdc178edcaaae0d17b7361270dd59a1f592d6469: Additional verification measures
- ChapterNumber: 6.3
- ObjectType: DocItem

#### ef019add2131d868f70fa675970a8ee544acab6c5545beed8dc1cc1dff79a288: Additional verification of E2EConfig file
- ChapterNumber: 6.3.1
- ObjectType: DocItem

##### c1eec9b58ced323fb540424e75012872ef7521badcbcf77c82952884444936e0
The user of MICROSAR Safe shall ensure that the length of the following identifiers can be uniquely identified by the compiler and linker.
The following strings are internal identifiers:
- E2EPW_Marshal_pde_h
- E2EPW_CheckDeserial_pde_h
- E2EPW_node_port_pde_RX_H
- E2EPW_node_port_pde_TX_H
The following strings are external identifiers:
- E2EPW_Marshal_pde
- E2EPW_CheckDeserial_pde
- E2EPW_Init_p_o_rx
- E2EPW_Init_p_o_tx
- E2EPW_Get_SenderState_p_o
- E2EPW_Get_ReceiverState_p_o
- E2EPW_Write_p_o
- E2EPW_Read_p_o
This requirement applies for all PAs in the E2EConfig with node, p(ort) and pde/o. The number of significant initial characters of the compiler and linker can usually be found in their documentation.
- ForeignTraceId: SMI-126
- ForeignAlternativeId: SMI-43713645-D4D8-4E2F-95CA-E0EEB091A782
- ObjectType: RQM_SAFETY_MANUAL_ITEM

##### d93a20ff827ea06e13876251c4f34ff02233461e071c2241d537c2e03ecaadf7
The user of MICROSAR Safe shall verify that all PAs in an E2EConfig with the same PDE_Name have the same values in the following fields:
- PDE_Type
- Byte_Order_CPU
- Bit_Order
- Bit_Counting
- Unused_Bit_Value
- Category
- Data_Length
- Is_Opaque
- ForeignTraceId: SMI-127
- ForeignAlternativeId: SMI-879BE081-170C-40C5-A9A7-29361F7DF502
- ObjectType: RQM_SAFETY_MANUAL_ITEM

##### 425df1a0631fd9e10c71d91d369820b050c09e29062c909fb42ff897774d7e45
The user of MICROSAR Safe shall verify that each signal in a PA is also be defined in all other PAs with same PDE_Name, and the signals must also have the same values in the following fields:
- Signal_Name
- Signal_Type
- Signal_Property
- Byte_Order
- Bit_Length
- Bit_Position
- ForeignTraceId: SMI-128
- ForeignAlternativeId: SMI-B5C1B9AB-2CD5-402D-9227-F0904C4E87B8
- ObjectType: RQM_SAFETY_MANUAL_ITEM

##### f0b4154c2eb097c7a89823292ff349f0d336dadca7c538834a7b1d7610fc9fad
The user of MICROSAR Safe shall verify that the attributes of each PA are defined in the E2EConfig as intended.
| Attribute | Requirement |
| --- | --- |
| PDE_Type | PDE_Type shall equal the data type of the corresponding PDE in the AUTOSAR application and the RTE functions that are invoked by the E2EPW code. |
| Node_Name | Node_Name shall equal the name of the SWC. The preprocessor sets Node_Name to the SWC's name. If you do not use the preprocessor or manipulate the E2EConfig file, then make sure that the requirement is still met. |
| Direction | Direction shall equal the direction expected for the corresponding PDE in the RTE. |
| Byte_Order_CPU | Byte_Order_CPU shall equal the byte order of the used CPU. |
| Unused_Bit_Value | Unused_Bit_Value shall equal the fillbit configured in the COM layer for the I-PDU representation of the PDE. |
| Check_DeSerial | Check_DeSerial shall be set to YES if it is required that the E2EPW code checks for deserialization errors on the receiver side. |
| Includes_H | Includes_H shall list the header file that defines the data type of the PDE, the header file that defines the type Rte_Instance (if used) and the header file that defines RTE_E_OK. |
| Includes_C | Includes_C shall list the header file(s) that declare(s) the functions Rte_Read_p_o (), Rte_Write_p_o () and Rte_IsUpdated_p_o () (if used). This requirement only applies if the header files are not already included in the field "Includes_H". |
| Category | Category shall equal the short name of the E2Elib profile selected for the PDE. |
| Data_Length | Data_Length shall equal the bit-length of the I-PDU representation of the PDE. |
| Data_ID and Data_ID_List | Data_IDs and _Data_ID_List shall fulfill the requirements of the respective E2E profile. |
| Max_Delta_Counter_Init | Max_Delta_Counter_Init shall equal the required initial value of MaxDeltaCounter of the E2E library communication state for the PDE. |
| Data_Id_Mode | Data_Id_Mode shall equal the requirements from the respective E2E profile. |
| Offset | Offset shall equal the communication specification by the OEM. |
| Max_No_New_Or_Repeated_Data | Max_No_New_Or_Repeated_Data shall equal the requirements from the respective E2E profile. |
- ForeignTraceId: SMI-131
- ForeignAlternativeId: SMI-A4B44F0A-E2BD-4DC5-B9C9-F324208F9130
- ObjectType: RQM_SAFETY_MANUAL_ITEM

##### 5ee3c0a3b37e07b58bdbe6367d8f70938f99534aea8ebd5e2e29a5a8b4faa673
The user of MICROSAR Safe shall verify that each signal that is configured in a PA shall be assigned to a signal in the corresponding PDE in the RTE. Vice versa, each signal in the PDE in the RTE shall be assigned to a signal in the corresponding PA.
If a signal in the RTE is not configured for protection, it will not be protected.
Note that the set of signals in the PA represents the corresponding signal group in the PDE.
| Attribute | Requirement |
| --- | --- |
| Port_Name | Port_Name shall equal the Port Prototype name that is used by the RTE for the related data element in the RTE. |
| VDP_Name | VDP_Name shall always be equal to PDE_Name. VDP_Name shall equal the VDP name that is used by the RTE for the related data element in the RTE. |
| Is_Opaque | Is_Opaque shall always be FALSE. The option Is_Opaque is for future versions of the E2EPW. It allows to pass PAs as UINT8-arrays without the necessity of marshaling. The E2EPW then treats the data element as opaque (no marshaling is performed). |
| Use_Call_By_Ref | Use_Call_By_Ref shall be YES if the data element is not a primitive data type or configured for reception. If YES, then a pointer to the data element is passed as an argument to Rte_Read_p_o() and Rte_Write_p_o(), respectively ("call by reference"). If NO, then the value of data element is passed ("call by value"). Note that for Rte_Read_p_o(), Use_Call_By_Ref is always YES. |
| Use_Rte_Update | Use_Rte_Update shall be YES if and only if the protection wrapper shall check for new received data elements on the RTE level before calling Rte_Read_p_o(). If YES, then Rte_Read_p_o() is only called if Rte_IsUpdated_p_o() returns TRUE before. If NO, then Rte_Read_p_o() is always called. Note that Rte_IsUpdated_p_o() is only available in AUTOSAR 4.0 or higher. |
| Use_Rte_Instance | Use_Rte_Instance shall be YES if and only if the instance parameter is required as an argument for Rte_Write_p_o(), Rte_Read_p_o() and Rte_IsUpdated_p_o(). Note that the instance parameter is currently not interpreted by the E2EPW, hence different instances share the same E2EPW and E2E library code and data. Therefore, Use_Rte_Instance may only be YES if each port p and data element o is not used by more than one instance. |
The user of MICROSAR Safe shall verify that the combination of Port_Name and VDP_Name is unique over all PDEs for the same node.
- ForeignTraceId: SMI-130
- ForeignAlternativeId: SMI-A3500BA9-6729-40C4-9E28-62E42274DDFE
- ObjectType: RQM_SAFETY_MANUAL_ITEM

##### 55c097720565c085abe77d4e351076c744bdfcc8bfa1b2ca47a9428b8e20f94d
The user of MICROSAR Safe shall verify that the attributes of each signal in a PA are defined in the E2EConfig as intended.
| Attribute | Requirement |
| --- | --- |
| Signal_Name | Signal_Name shall equal the name of the corresponding signal in the data element in the RTE. |
| Signal_Type | Signal_Type shall equal the type of the corresponding signal in the data element in the RTE. |
| Byte_Order | Byte_Order shall equal the byte order that is defined for the corresponding signal in the I-PDU for the I-PDU mapping in the COM layer. |
| Bit_Length | Bit_Length shall equal the bit length of the corresponding signal in the I-PDU. |
| Bit_Position | Bit_Position shall equal the start-bit position of the corresponding signal relative to the protected signal group (protected area) and depending on the endianess. If the signal is mapped with Little Endian in the I-PDU, then Bit_Position is the least significant bit's position in the least significant byte. If the signal is mapped with Big Endian in the I-PDU, then Bit_Position is the most significant bit's position in the most significant byte. For a signal of type UINT8N, the Bit_Position is the least significant bit's position in the byte with the lowest address. |
- ForeignTraceId: SMI-132
- ForeignAlternativeId: SMI-EEB575CF-FF3E-4C11-B220-52554FDBFB88
- ObjectType: RQM_SAFETY_MANUAL_ITEM

##### 9dd0e2b46d0e5f59051e383c592845523a24fd284b0ef61d52ab851509d9969e
The user of MICROSAR Safe shall verify that for all instances of a PDE of the corresponding PA in the various E2EConfig files,
- the profile configurations are equal throughout all PA instances (except Max_Delta_Counter_Init),
- all signal configurations are equal throughout all PA instances (except Signal_Name and Signal_ID) and
- the following field values are equal throughout all PA instances:
- Bit_Order
- Bit_Counting
- Unused_Bit_Value
For example, a sender PDE and a receiver PDE on different ECUs must be configured in different E2EConfig files.
- ForeignTraceId: SMI-133
- ForeignAlternativeId: SMI-B7CB9130-5D70-498C-B44F-C54128615B0F
- ObjectType: RQM_SAFETY_MANUAL_ITEM

#### 922f0b4c041af3c936a670e17bccca2e6cf1e29ca3916cc5da9ab18e384c103e: Additional verification of generator execution
- ChapterNumber: 6.3.2
- ObjectType: DocItem

##### 39452eadde66eb20aefe584464cd3aa962236ffac83c73bb5cf268c1a930d6f8
The user of MICROSAR Safe shall ensure that the output path for the generated E2EPW code (command-line argument "outpath-path") shall be empty before the generator is started.
If the output path is not empty, code from previous generation runs may be accidentally integrated into the system.
This requirement is fulfilled if generation is performed using DaVinci Configurator PRO.
- ForeignTraceId: SMI-134
- ForeignAlternativeId: SMI-143DB92C-C8E6-405A-93F6-722CF7B0F2E7
- ObjectType: RQM_SAFETY_MANUAL_ITEM

##### 769524f04cc32c6c52f4bae6ddc294a975f7086a51cc30720bfd07c15ad750ee
The user of MICROSAR Safe shall inspect the messages of the E2EPW generator execution.
If the generator aborts the generation process with an error message, the (partially) generated output files shall not be used in the system.
If the generator detects an error, a message starting with "ERROR" is displayed on the standard output.
If the generator shows a warning message starting with "WARNING", the user of MICROSAR Safe shall ensure that the cause of the warning does not invalidate the generated output files.
The generator shows a warning message in the following cases:
1. The E2EConfig file ends with some text after the configuration definitions of all protected areas.
2. The E2EConfig file has at least two PDEs defined with the same PDE_Name.
It is strongly recommended to analyze these cases.
- ForeignTraceId: SMI-135
- ForeignAlternativeId: SMI-AAAA7A11-5BBA-4BE4-9333-18B12030681E
- ObjectType: RQM_SAFETY_MANUAL_ITEM

##### 59f257d34c825b13e8106bfb0118de1045d60d146ddf17f9b71220f66f2b18f7
The user of MICROSAR Safe shall verify that each generated file is complete, i.e. each file must end with an "EOF" comment.
- ForeignTraceId: SMI-142
- ForeignAlternativeId: SMI-C96B2FDA-6894-42F6-8B8A-91B24570F5DE
- ObjectType: RQM_SAFETY_MANUAL_ITEM

#### 1d9a9fc5068672307ae2e0479945fdc435f763fa0ac2fcab187ed08310ad3b90: Additional verification for application
- ChapterNumber: 6.3.3
- ObjectType: DocItem

##### 47ed8938f9977969917fe4858b8736e10921856e95dabcc192c555005f736ae2
The user of MICROSAR Safe shall verify that the E2E library communication states are not modified by the application while an E2EPW API function is running.
If a pointer to the senders/receivers E2E library communication state is required, it shall be queried with E2EPW_GetProtectState_p_o() / E2EPW_GetCheckState_p_o().
Make sure that the values of the E2E library communication state are only read and not altered by the application or a module other than the E2EPW or the E2E library unless intended so.
For special purposes, modification of the sequence counter by the application may be useful or required. Be aware that this is done in the responsibility of the user of MICROSAR Safe.
- ForeignTraceId: SMI-136
- ForeignAlternativeId: SMI-FEA226CE-FAF6-4C51-B19F-E55947D79491
- ObjectType: RQM_SAFETY_MANUAL_ITEM

##### 6a5af563dd070e0d5a7dff5d791a2174de61442b3d2ebed876540d5b4c980f0c
The user of MICROSAR Safe shall verify that, when a data element is passed to E2EPW_Write_p_o() or E2EPW_Read_p_o() using call by reference, then the data element is not altered while E2EPW_Write_p_o() or E2EPW_Read_p_o() is running.
- ForeignTraceId: SMI-137
- ForeignAlternativeId: SMI-51FA6251-BD6E-4A35-A751-DAA7CD63D016
- ObjectType: RQM_SAFETY_MANUAL_ITEM

##### a2034f07ece46583b0f49e0c9f12831639eb1c669ab84707180242d44d2008cc
The user of MICROSAR Safe shall verify that an E2EPW API function for a certain port / pde combination is not called while another or the same E2EPW API function is running for the same combination.
This applies to the following functions:
- E2EPW_WriteInit_p_o(), Note: E2EPW_WriteInit_p_o() is not reentrant
- E2EPW_Get_ProtectState_p_o()
- E2EPW_Write_p_o()
- E2EPW_ReadInit_p_o(), Note: E2EPW_ReadInit_p_o() is not reentrant
- E2EPW_Get_CheckState_p_o()
- E2EPW_Read_p_o()
- ForeignTraceId: SMI-141
- ForeignAlternativeId: SMI-D21261A3-432F-4D04-8BEF-0827D62C9ACE
- ObjectType: RQM_SAFETY_MANUAL_ITEM

##### 3c17ab85e914417685cc00c964a41f83350dd90724accc256439ba4333f35209
The user of MICROSAR Safe shall verify that the E2E library communication state is checked for plausibility with E2EPW_Get[Protect|Check]State_p_o() after a startup/restart.
- ForeignTraceId: SMI-138
- ForeignAlternativeId: SMI-9C1ECD2B-4D64-4C06-B063-774D2D439EE6
- ObjectType: RQM_SAFETY_MANUAL_ITEM

##### 8f98d557186f2f1e985dc8319f5bf953d81edd63f4f0a49ef0810937a47f4afb
The user of MICROSAR Safe shall verify that that E2EPW_ReadInit_p_o() and E2EPW_WriteInit_p_o() is only called at partition startup/restart.
Note: E2EPW_ReadInit_p_o() and E2EPW_WriteInit_p_o() have to be called prior to any other E2EPW API function call.
This initializes the communication state on sender and receiver side. The E2E library communication state should be initialized when the application is initialized or reset.
- ForeignTraceId: SMI-139
- ForeignAlternativeId: SMI-861C047E-BD2C-44CD-BBB8-239E0D71A8BD
- ObjectType: RQM_SAFETY_MANUAL_ITEM

##### 7de2b83d8290ebda12fcaadce489aa27e7594ab48be56295915e83617582f69a
The user of MICROSAR Safe shall verify that the intended parameters are passed. This especially applies to:
- instance IDs. Note: only one instance ID is used for each p, o combination.
- AppData parameter for E2EPW_Write_p_o() and E2EPW_Read_p_o()
- ForeignTraceId: SMI-140
- ForeignAlternativeId: SMI-19DFFA35-5726-476D-94F9-E19932735FF6
- ObjectType: RQM_SAFETY_MANUAL_ITEM

### c1e544b2aa65784ff8154a1c4a60cea300543a681b0537699592d04a94550ade: Dependencies to other components
- ChapterNumber: 6.4
- ObjectType: DocItem

#### e11d344bb1d320f208666ad6d15700eee07d4e7755a7cd65d17d9d96eaa1a1c9: Safety features required from other components
- ChapterNumber: 6.4.1
- ObjectType: DocItem

##### 8cd59e51479d95ef98f977d1a810ebeffb91121fde481c8766e240a83545ce87
This component requires the initialization, protection, mapping and check features from the E2E library as safety features.
- ForeignTraceId: SMI-129
- ForeignAlternativeId: SMI-97695159-CFEC-402F-B39F-886CEFAFFFA9
- ObjectType: RQM_SAFETY_MANUAL_ITEM

#### dc97fd70bd595565d42f84477113090afc2f19189e253e0d431f12f6d60a11c0: Coexistence with other components
- ChapterNumber: 6.4.2
- ObjectType: DocItem

##### d906cd3ffe8ae9370b395b77eac5129d5a3a41180c6b80fa9db6c9d8b9ea76bb
This component requires coexistence with the used Rte.
It is assumed that the user of E2EPW has the required ASIL.
- ForeignTraceId: SMI-144
- ForeignAlternativeId: SMI-4A3D4E98-F543-450A-BAFA-EBA440CBE984
- ObjectType: RQM_SAFETY_MANUAL_ITEM

### b02a378d477b097b7f523511829dd28013e805acef8234ebdb62283e7187df3f: Dependencies to hardware
- ChapterNumber: 6.5
- ObjectType: DocItem

#### 55ae004315a93889d8d2f24eb2b2a8583e2b18703d6f4fabb5bdec7e0d8886da
This component does not use a direct hardware interface.
- ObjectType: DocItem

## 5a0ecaae814019517fd2548912dacf59cbd5bf850b9908cdc5c5e93a955d6151: Safety Manual E2EXf
- ChapterNumber: 7
- ObjectType: DocItem

### d55a80081cdd2301c7ecf97f81032fa591659d3fe8cd40001681a8d95ce1af5d: Assumed safety requirements
- ChapterNumber: 7.1
- ObjectType: DocItem

#### 8824c61a2ddb8957b8778c12f2719a6437fc66431f266c75d1f965353f6dcc71
This component assumes the following safety requirements:
| ID | Safety Requirement | Associated TSR | ASIL |
| --- | --- | --- | --- |
| CREQ-131007 | E2EXf shall provide a service to initialize itself. | TSR-1 | ASIL D |
| CREQ-131011 | E2EXf shall provide a service to protect data. | TSR-10,TSR-111108 | ASIL D |
| CREQ-133278 | E2EXf shall provide a service to verify protected data. | TSR-10,TSR-111108 | ASIL D |
This component in addition to the assumed safety requirements ensures freedom from interference with respect to memory (and timing) with up to ASIL D.
- ForeignTraceId: SMI-62928
- ForeignAlternativeId: SMI-2112D033-DFD1-4860-B484-149DBB44D8EE
- ObjectType: RQM_SAFETY_MANUAL_ITEM

### be1bae2e790c91c0a5d285256c9455abb50b10a39179fbbd932caa7d4fa0ceae: Configuration constraints
- ChapterNumber: 7.2
- ObjectType: DocItem

#### febae8246f268ac775532e8f1bbd9216dd19423f2e450384a08ed8a0eb74d9cb
This component does not have configuration constraints.
- ObjectType: DocItem

### 80a8d0fb4f09551d5e96405d282b0f6e91e253fd2d753ccc399adc3d816ba5b7: Additional verification measures
- ChapterNumber: 7.3
- ObjectType: DocItem

#### 5a6e519c0d394873d72e96fed210d25d79b43b934c3e9b98530c70c42bb8c751
Please note that the E2EXf Generator and RTE Analyzer only implement measures to detect systematic faults by the software. No measures are implemented to detect or mitigate random faults on the computer used for generation.
- ObjectType: DocItem

#### 6837280fdc7ff4dd323210a067efda83a192ded594d1d2bbb64cde4d19d30b06
The user of MICROSAR Safe shall execute the RTE Analyzer.
The RTE Analyzer performs checks to identify faults in E2EXf. Especially out-of-bounds accesses within E2EXf are detected. If RTE Analyzer reports a fault, the generated E2EXf cannot be used. Moreover it provides the user of MICROSAR Safe with feedback what was generated. This feedback shall be reviewed during integration testing against the intended software design and its configuration.
Please see the Technical Reference of the RTE Analyzer how to execute it.
- ForeignTraceId: SMI-62927
- ForeignAlternativeId: SMI-9AF4D0B9-EA1F-4798-9746-3FC26313DE4C
- ObjectType: RQM_SAFETY_MANUAL_ITEM

#### 2aede1b5bd0b36bacb89c2c9f5e7e8ef8536ef683a7f7baa59f71183619f7e8e: Guided integration testing
- ChapterNumber: 7.3.1
- ObjectType: DocItem

##### f39c4d5f6d53f531dc5237909bde2b95262013e2b7b1f950709d9e8b35c100b2
Residual faults in the E2EXf Generator can only be found during integration testing. Vector assumes that the user of MICROSAR Safe performs an integration testing and verification of software safety requirements according to ISO 26262 Part 6 Clauses 10 and 11 (see also SMI-4). To support this integration testing the RTE Analyzer produces a configuration feedback report.
Please refer to the Technical Reference of the RTE Analyzer for a description of the configuration feedback report.
The following subsections describe the requirements that must be fulfilled during integration testing and verification of software safety requirements.
Each Safety Manual Item (SMI) is structured in the following way:
- The requirement that must be fulfilled
- Explanation of the requirement and a rationale
- Recommended configuration constraints (optional)
- Recommended means of complying with the requirement (optional)
- Details on the information provided by the RTE Analyzer supporting this requirement
- ObjectType: DocItem

##### 911ac0471984e97578ae9d5c9f76483100601ed9282d0e853c988f4eb6e1f0a5
The user of MICROSAR Safe shall ensure that the E2E configuration is as expected.
This requires verification of:
- Profile
- E2E header length
- Input header length
- Execute with no data
- Check incoming data
- Window size (4.4 State Machine)
- Window size init (19-11 State Machine)
- Window size invalid (19-11 State Machine)
- Window size valid (19-11 State Machine)
- Clear from valid to invalid (19-11 State Machine)
- Transit to invalid extended (19-11 State Machine)
- State changes
- Offset of counter
- Offset of CRC
- Offset of data ID high byte
- Offset of E2E header
- Data ID
- Data ID nibble mode
- Data length
- Initial max. allowed counter gap
- Max. missing or repeated data
- Initial counter sync data
- Max. allowed counter gap
for every E2E protected data element.
Verification can e.g. be performed by review of the configuration feedback report against the communication extract and the E2ELIB specification (e.g. for the E2E header length).
Input header length refers to the length of the payload header e.g. SOMEIPXF header length.
Vector assumes integration testing on vehicle network level using fault-injection is used to additionally verify the effectiveness of the E2E protection.
The RTE Analyzer lists the RTE APIs that use E2E transformation to assist in this integration step.
The RTE Analyzer lists the E2E configuration to assist in this integration step.
E2EXF configurations for which the check of incoming data is disabled are not listed.
- ForeignTraceId: SMI-62932
- ForeignAlternativeId: SMI-EDC4F818-405B-4371-AF31-6E952A1A9940
- ObjectType: RQM_SAFETY_MANUAL_ITEM

### 7a044f1ecf97d23db488fe38088cfd0f9e22ab97c70f4576a5e7d6e7664002f9: Safety requirements required from other components
- ChapterNumber: 7.4
- ObjectType: DocItem

#### 317c3cd090029780e067ad0520037303c879243588eeb2bc0829d45701cad9b3
E2EXF requires the following functionality as safety requirement from the E2ELIB:
- data protection
- initialization of protection state
- checking of protection state
- mapping of result state to state machine status
- checking of data
- initialization of state machine
This requirement is fulfilled if an ASIL E2ELIB by Vector is used.
- ForeignTraceId: SMI-66294
- ForeignAlternativeId: SMI-35871402-808C-4BCA-BB0F-D67A80A0E07B
- ObjectType: RQM_SAFETY_MANUAL_ITEM

#### f7dc269a90644b25f2dffd0b422a106d3956b652a81c3cb450b323e2f9d06bf8
E2EXF requires the following functionality as safety requirements from the RTE:
- Transformer handling (TSR-10)
For components provided as part of MICROSAR Safe, the respective section of the Safety Manual for that component allows you identifying if this requirement is fulfilled.
- ForeignTraceId: SMI-857105
- ForeignAlternativeId: SMI-AC58EB42-A37A-4291-9E2A-60B8A4D3FA70
- ObjectType: RQM_SAFETY_MANUAL_ITEM

### 55205326405913de9ccfa5e816a56a327308baff51703411d42158ce169373d7: Dependencies to hardware
- ChapterNumber: 7.5
- ObjectType: DocItem

#### 65f8663e9035072beaf97b6e541ba9b420e5bc8618bbca9b217ca0d4d3929fc2
This component does not use a direct hardware interface.
- ObjectType: DocItem

## c3f67ca40bbc57f958223ff23181ea35c82e5949330350bd98b8c509518ff988: Safety Manual EcuM
- ChapterNumber: 8
- ObjectType: DocItem

### 99232968e761672eddca84b3634024211d64dd4c3256ca9fbe3aec4f6c89f07d: Assumed safety requirements
- ChapterNumber: 8.1
- ObjectType: DocItem

#### 7427f22ac52934aa606713106478fcd021127da2e8ddc1cef1d960c169faf765
This component assumes the following safety requirements:
| ID | Safety Requirement | Associated TSR | ASIL |
| --- | --- | --- | --- |
| CREQ-470 | EcuM shall provide a service to initialize the ECU management. | TSR-1 | ASIL D |
| CREQ-389 | EcuM shall provide a service to complete the startup phase. | TSR-1 | ASIL D |
| CREQ-543 | EcuM shall perform validation of all postbuild configurable BSW module configuration parameters. | TSR-1 | ASIL D |
| CREQ-525 | EcuM shall provide a callout to initialize driver prior the start of the OS. | TSR-1 | ASIL D |
| CREQ-488 | EcuM shall provide a callout to determine the Postbuild configuration data. | TSR-1 | ASIL D |
| CREQ-505 | EcuM shall provide a callout to initialize drivers prior Postbuild data is available. | TSR-1 | ASIL D |
| CREQ-509 | EcuM shall provide a callout to re-initialize drivers during a restart. | TSR-1 | ASIL D |
| CREQ-454 | EcuM shall provide ECU initialization on partitions. | TSR-1 | ASIL D |
| CREQ-494 | EcuM shall handle ECU phases on MultiCore ECUs. | TSR-100551 | ASIL D |
| CREQ-473 | EcuM shall provide a callout to synchronize the master and slave cores during shutdown. | TSR-100551 | ASIL D |
- ForeignTraceId: OBJ1138932
- ForeignAlternativeId: OBJ-0933ABE8-7F6A-4E3B-BA1D-F6D5E1EC5B13
- ObjectType: TRACE_ITEM

#### e0669eb45db522f379980a42ba0433887715e49b508420316cf790dde623bd08
This component in addition to the assumed safety requirements ensures freedom from interference with respect to memory with up to ASIL D.
- ObjectType: DocItem

### 5010b997f016a96b524dc0c8f103e48fd46e8dc90fe0d3f2f6645e255e3220f2: Configuration constraints
- ChapterNumber: 8.2
- ObjectType: DocItem

#### 3207b6aa691b230adbce2e601314f845b0331a83a3c351a0af4bb16425e4439a
The user of MICROSAR Safe shall configure the attribute /MICROSAR/EcuM/EcuMFlexGeneral/EcuMEnableDefBehaviour to FALSE.
This setting is enforced by a MSSV plugin.
- ForeignTraceId: SMI-823269
- ForeignAlternativeId: SMI-2031490C-123C-4F65-9E0E-DCB1E58501CC
- ObjectType: RQM_SAFETY_MANUAL_ITEM

#### 6ee91995706aacb34dbb3dc255567c74e002e3ca854710dbdc1dd9af62f7635c
The user of MICROSAR Safe shall not configure
any reference in /MICROSAR/EcuM/EcuMConfiguration/EcuMCommonConfiguration/EcuMWakeupSource/EcuMComMPNCRef to a PNC for a wakeup source.
This setting is enforced by a MSSV plugin.
- ForeignTraceId: SMI-823270
- ForeignAlternativeId: SMI-4DF05155-E224-4225-8965-970F482CDE81
- ObjectType: RQM_SAFETY_MANUAL_ITEM

### d6ae963fc55c956873e077e109b63578d5af3931dc76b6bc52186ab1c021407c: Additional verification measures
- ChapterNumber: 8.3
- ObjectType: DocItem

#### 127b8e6e9e406839a2eb4bb2201c869e3b5e4265dee34a39dcfe7ceeb7b0f740
The user of MICROSAR Safe shall ensure the intended initialization procedure during integration testing.
The user of MICROSAR Safe shall ensure the intended initialization procedure by performing the following tests:
- Start the ECU and verify that the intended initalization routines are called. This needs to be verified for each Postbuild-selectable configuration.
- Corrupt the Postbuild data and the corresponding CRC in non-volatile memory and start the ECU. Then verify that the corruption is detected by EcuM.
- Start the ECU and verify that the intended Postbuild-selectable configuration is used by the EcuM. This needs to be verified for each Postbuild-selectable configuration.
A start of the ECU includes a "cold-start", reset as well as wake-up from sleep if applicable.
This requirement is only applicable if TSR-1 is assumed as a safety requirement.
- ForeignTraceId: SMI-39
- ForeignAlternativeId: SMI-0B070E1D-1172-4D94-8AAA-CEF620E2D180
- ObjectType: RQM_SAFETY_MANUAL_ITEM

### 45ddd42453f561b9909733cd1afa5c47dfc20973d02b0f1df3dc9564b0b51d97: Safety requirements required from other components
- ChapterNumber: 8.4
- ObjectType: DocItem

#### d6b14499f759024f799b343c4cb8bd1a3c86737dd13622a8c8ab88f95c834995
This component requires the OS service to get the core ID functionality as an assumed safety requirement (TSR-1) from other interfacing components.
For components provided as part of MICROSAR Safe, the respective section of the Safety Manual for that component allows you identifying if this requirement is fulfilled.
This requirement is only applicable if TSR-1 is assumed as a safety requirement.
- ForeignTraceId: SMI-42
- ForeignAlternativeId: SMI-BB7FC544-1E1B-4736-A244-5F6C006B86C5
- ObjectType: RQM_SAFETY_MANUAL_ITEM

### 3e83ef487418c227a74d67fa1ddbc3d0fec8969dc05755b94806666c4551b832: Dependencies to hardware
- ChapterNumber: 8.5
- ObjectType: DocItem

#### 2b57fa111105f9d4b6ccfa74c290fb96847bd2f6293dc9c85116ba57d639d76b
This component does not use a direct hardware interface.
- ObjectType: DocItem

## 0789133811b1b4c1ce39dfe984efe30ea2bdd64cba23217ef99396ac2701edd6: Safety Manual Os
- ChapterNumber: 9
- ObjectType: DocItem

### 8c9b6ca0d68dbf07db5e864494d168882766c4cb46cab4831034a6d3ec062c87: Safety requirements
- ChapterNumber: 9.1
- ObjectType: DocItem

#### 43e0da473ecfaa5dfd4c7476b8836a4d3ced41fcd8411c47223e25d819941519
This component assumes the following safety requirements:
| ID | Safety Requirement | Associated TSR | ASIL |
| --- | --- | --- | --- |
| CREQ-118 | OS shall provide different application modes. | TSR-1 | ASIL D |
| CREQ-63 | OS shall provide a service to start the OS. | TSR-6,TSR-1 | ASIL D |
| CREQ-162 | OS shall provide a service to initialize itself. | TSR-1,TSR-6 | ASIL D |
| CREQ-51 | OS shall automatically start a subset of alarms for an application mode. | TSR-6 | ASIL D |
| CREQ-146 | OS shall automatically start a subset of tasks for an application mode. | TSR-6 | ASIL D |
| CREQ-72 | OS shall automatically start a subset of schedule tables for an application mode. | TSR-6 | ASIL D |
| CREQ-117 | OS shall provide a service to get the current application mode. | TSR-6 | ASIL D |
| CREQ-45 | OS shall provide a global callback during OS startup. | TSR-6 | ASIL D |
| CREQ-299 | Os shall synchronize the startup in multi-core systems. | TSR-6 | ASIL D |
| CREQ-153 | OS shall provide a service to shutdown the OS. | TSR-6 | ASIL D |
| CREQ-95 | OS shall provide a service to shutdown all cores synchronously. | TSR-6 | ASIL D |
| CREQ-161 | OS shall provide a global callback upon shutdown. | TSR-6 | ASIL D |
| CREQ-89 | OS shall provide tasks. | TSR-16,TSR-6,TSR-7,TSR-12,TSR-8,TSR-9 | ASIL D |
| CREQ-58 | OS shall provide basic tasks. | TSR-6,TSR-7,TSR-12,TSR-16,TSR-9,TSR-8 | ASIL D |
| CREQ-20 | OS shall provide extended tasks. | TSR-7,TSR-6,TSR-16,TSR-12,TSR-9,TSR-8 | ASIL D |
| CREQ-71 | OS shall provide a global callback directly before a task starts its execution. | TSR-6,TSR-8,TSR-7 | ASIL D |
| CREQ-165 | OS shall provide a global callback directly before a task finishes its execution. | TSR-6,TSR-8,TSR-7 | ASIL D |
| CREQ-42 | OS shall provide a service to activate a task. | TSR-6,TSR-8,TSR-7,TSR-9 | ASIL D |
| CREQ-28 | OS shall handle multiple activations of basic tasks. | TSR-6 | ASIL D |
| CREQ-101 | OS shall provide a service to terminate the calling task. | TSR-9,TSR-6 | ASIL D |
| CREQ-121 | OS shall provide a service to define the next activated task. | TSR-6 | ASIL D |
| CREQ-126 | OS shall provide a service to explicitly invoke the scheduler. | TSR-6 | ASIL D |
| CREQ-80 | OS shall provide a service to get the ID of the current task. | TSR-6 | ASIL D |
| CREQ-74 | OS shall provide a service to get the state of a given task. | TSR-6 | ASIL D |
| CREQ-135 | OS shall provide a service to declare a task. | TSR-6 | ASIL D |
| CREQ-131845 | OS shall provide category 0 ISRs. | TSR-6 | ASIL D |
| CREQ-103 | OS shall provide category 1 ISRs. | TSR-6 | ASIL D |
| CREQ-355 | OS shall provide category 2 ISRs. | TSR-9,TSR-8,TSR-7,TSR-6 | ASIL D |
| CREQ-115 | OS shall provide a service to execute a callback in category 2 ISRs. | TSR-6,TSR-9,TSR-7 | ASIL D |
| CREQ-16 | OS shall provide a service to get the ID of the currently executing category 2 ISR. | TSR-7,TSR-6 | ASIL D |
| CREQ-24 | OS shall handle un-configured interrupt sources. | TSR-6 | ASIL D |
| CREQ-78 | OS shall provide a service to determine the interrupt source of a non-configured interrupt upon handling of such interrupt. | TSR-6 | ASIL D |
| CREQ-1200 | OS shall allow usage of interrupt services before start and after shutdown of the OS. | TSR-1 | ASIL D |
| CREQ-154 | OS shall provide a nestable service to disable all interrupts. | TSR-101876,TSR-6 | ASIL D |
| CREQ-98 | OS shall provide a nestable service to enable all interrupts. | TSR-6,TSR-101876 | ASIL D |
| CREQ-151 | OS shall provide a nestable service to disable all category 2 interrupts. | TSR-101876,TSR-6 | ASIL D |
| CREQ-82 | OS shall provide a nestable service to enable all category 2 interrupts. | TSR-101876,TSR-6 | ASIL D |
| CREQ-111 | OS shall provide a non nestable service to disable all interrupts. | TSR-101876,TSR-6 | ASIL D |
| CREQ-43 | OS shall provide a non nestable service to enable all interrupts. | TSR-101876,TSR-6 | ASIL D |
| CREQ-1257 | OS shall provide a non nestable service to disable all interrupts callable from kernel mode. | TSR-6,TSR-101876 | ASIL D |
| CREQ-1259 | OS shall provide a non nestable service to enable all interrupts callable from kernel mode. | TSR-6,TSR-101876 | ASIL D |
| CREQ-1256 | OS shall provide a non nestable service to disable all interrupts callable from user mode. | TSR-6,TSR-101876 | ASIL D |
| CREQ-1258 | OS shall provide a non nestable service to enable all interrupts callable from user mode. | TSR-101876,TSR-6 | ASIL D |
| CREQ-108741 | OS shall provide a non nestable service to disable all interrupts callable from any mode. | TSR-6,TSR-101876 | ASIL D |
| CREQ-108742 | OS shall provide a non nestable service to enable all interrupts callable from any mode. | TSR-101876,TSR-6 | ASIL D |
| CREQ-108744 | OS shall provide a non nestable service to disable all category 2 interrupts callable from kernel mode. | TSR-6,TSR-101876 | ASIL D |
| CREQ-108747 | OS shall provide a non nestable service to enable all category 2 interrupts callable from kernel mode. | TSR-6,TSR-101876 | ASIL D |
| CREQ-108743 | OS shall provide a non nestable service to disable all category 2 interrupts callable from user mode. | TSR-6,TSR-101876 | ASIL D |
| CREQ-108748 | OS shall provide a non nestable service to enable all category 2 interrupts callable from user mode. | TSR-101876,TSR-6 | ASIL D |
| CREQ-108745 | OS shall provide a non nestable service to disable all category 2 interrupts callable from any mode. | TSR-101876,TSR-6 | ASIL D |
| CREQ-108746 | OS shall provide a non nestable service to enable all category 2 interrupts callable from any mode. | TSR-6,TSR-101876 | ASIL D |
| CREQ-106181 | OS shall provide a service to disable a specific interrupt source. | TSR-1,TSR-6 | ASIL D |
| CREQ-106182 | OS shall provide a service to enable a specific interrupt source. | TSR-6,TSR-1 | ASIL D |
| CREQ-106183 | OS shall provide a service to clear pending interrupts. | TSR-1,TSR-6 | ASIL D |
| CREQ-114872 | OS shall provide a service to check whether or not the source of the given ISR is enabled. | TSR-6,TSR-1 | ASIL D |
| CREQ-114873 | OS shall provide a service to check whether or not the given ISR has been requested. | TSR-1,TSR-6 | ASIL D |
| CREQ-183488 | OS shall provide a service to enable multiple interrupt sources at once. | TSR-6 | ASIL D |
| CREQ-106 | OS shall provide events. | TSR-6 | ASIL D |
| CREQ-68 | OS shall provide a service to wait for the occurrence of events. | TSR-6 | ASIL D |
| CREQ-155 | OS shall provide a service to signal the occurrence of events to a task. | TSR-6 | ASIL D |
| CREQ-53 | OS shall provide a service to acknowledge the occurrence of events. | TSR-6 | ASIL D |
| CREQ-129 | OS shall provide a service to get the event states of a given task. | TSR-6 | ASIL D |
| CREQ-133 | OS shall provide a service to declare an event. | TSR-6 | ASIL D |
| CREQ-140 | OS shall provide counters. | TSR-111109,TSR-6 | ASIL D |
| CREQ-22 | OS shall provide a service to increment a counter. | TSR-6 | ASIL D |
| CREQ-156 | OS shall provide a service to get the current value of a counter. | TSR-6,TSR-111109 | ASIL D |
| CREQ-39 | OS shall provide a service to get the difference between a given and the current counter value. | TSR-111109,TSR-6 | ASIL D |
| CREQ-44 | OS shall provide a service for each hardware counter to translate a given period of time into number of ticks. | TSR-6 | ASIL D |
| CREQ-297 | OS shall provide a service for each hardware counter to translate number of counter ticks into a period of time. | TSR-6 | ASIL D |
| CREQ-1260 | OS shall provide a service to get the maximum possible value of a counter. | TSR-6 | ASIL D |
| CREQ-1261 | OS shall provide a service to get the number of underlying driver ticks required to reach a specific unit. | TSR-6 | ASIL D |
| CREQ-1262 | OS shall provide a service to get the minimum allowed number of ticks for a cyclic alarm of a counter. | TSR-6 | ASIL D |
| CREQ-138 | OS shall provide alarms. | TSR-6 | ASIL D |
| CREQ-116 | OS shall provide a service to set a relative alarm. | TSR-6 | ASIL D |
| CREQ-29 | OS shall provide a service to set an absolute alarm. | TSR-6 | ASIL D |
| CREQ-93 | OS shall provide a service to get an alarm. | TSR-6 | ASIL D |
| CREQ-164 | OS shall provide a service to cancel an alarm. | TSR-6 | ASIL D |
| CREQ-19 | OS shall provide a service to get the alarm base. | TSR-6 | ASIL D |
| CREQ-142 | OS shall provide alarm callbacks. | TSR-6 | ASIL D |
| CREQ-32 | OS shall provide a service to declare an alarm. | TSR-6 | ASIL D |
| CREQ-99 | OS shall provide schedule tables. | TSR-6 | ASIL D |
| CREQ-298 | OS shall provide expiry points. | TSR-6 | ASIL D |
| CREQ-14 | OS shall provide single-shot schedule tables. | TSR-6 | ASIL D |
| CREQ-67 | OS shall provide repeating schedule tables. | TSR-6 | ASIL D |
| CREQ-69 | OS shall provide explicitly synchronized schedule tables. | TSR-6,TSR-111109 | ASIL D |
| CREQ-81 | OS shall provide implicitly synchronized schedule tables. | TSR-6 | ASIL D |
| CREQ-61 | OS shall provide a service to start a schedule table at a relative value. | TSR-6 | ASIL D |
| CREQ-136 | OS shall provide a service to start a schedule table at an absolute value. | TSR-6 | ASIL D |
| CREQ-96 | OS shall provide a service to stop the processing of a schedule table. | TSR-6 | ASIL D |
| CREQ-112 | OS shall provide a service to switch the processing between different schedule tables. | TSR-6 | ASIL D |
| CREQ-100 | OS shall provide a service to start an explicitly synchronized schedule table synchronously. | TSR-6 | ASIL D |
| CREQ-152 | OS shall provide a service to synchronize a schedule table with a synchronization counter. | TSR-111109,TSR-6 | ASIL D |
| CREQ-25 | OS shall provide a service to stop synchronization of a schedule table. | TSR-6 | ASIL D |
| CREQ-108 | OS shall provide a service to query the state of a schedule table. | TSR-111109,TSR-6 | ASIL D |
| CREQ-36 | OS shall provide a mechanism to coordinate concurrent access to shared resources. | TSR-6,TSR-8 | ASIL D |
| CREQ-157 | OS shall provide linked resources. | TSR-8,TSR-6 | ASIL D |
| CREQ-66 | OS shall provide internal resources. | TSR-8,TSR-6 | ASIL D |
| CREQ-56 | OS shall provide a service to acquire a resource. | TSR-101876,TSR-8,TSR-6 | ASIL D |
| CREQ-107 | OS shall provide a service to release a resource. | TSR-8,TSR-101876,TSR-6 | ASIL D |
| CREQ-163 | OS shall provide a service to declare a resource. | TSR-6 | ASIL D |
| CREQ-15 | OS shall provide spinlocks. | TSR-8 | ASIL D |
| CREQ-17 | OS shall provide a service to acquire a spinlock. | TSR-8,TSR-101876,TSR-6 | ASIL D |
| CREQ-139 | OS shall provide a service to asynchronously acquire a spinlock. | TSR-101876,TSR-6,TSR-8 | ASIL D |
| CREQ-167 | OS shall provide a service to release a spinlock. | TSR-8,TSR-101876,TSR-6 | ASIL D |
| CREQ-208524 | OS shall provide a service to synchronize participating tasks at a referenced barrier. | TSR-6 | ASIL D |
| CREQ-354 | OS shall provide applications. | TSR-7,TSR-9,TSR-8 | ASIL D |
| CREQ-172 | OS shall provide a service to determine the application ID to which the current execution context was configured. | TSR-9,TSR-7,TSR-6,TSR-8 | ASIL D |
| CREQ-60 | OS shall provide a service to determine the application ID in which the current execution context is executed. | TSR-6,TSR-9,TSR-7,TSR-8 | ASIL D |
| CREQ-114 | OS shall provide a service to make an application accessible. | TSR-9,TSR-8,TSR-6,TSR-7 | ASIL D |
| CREQ-109 | OS shall provide a service to identify accessibility of OS objects . | TSR-9,TSR-8,TSR-7,TSR-6 | ASIL D |
| CREQ-18 | OS shall provide a service to identify object ownership. | TSR-8,TSR-7,TSR-6,TSR-9 | ASIL D |
| CREQ-110 | OS shall provide a service to terminate an application. | TSR-6,TSR-9,TSR-7,TSR-8 | ASIL D |
| CREQ-170 | OS shall provide restart tasks. | TSR-7,TSR-6,TSR-9,TSR-8 | ASIL D |
| CREQ-104 | OS shall provide a service to get the state of a given application. | TSR-7,TSR-6,TSR-8,TSR-9 | ASIL D |
| CREQ-34 | OS shall provide a service to call exported services from trusted applications. | TSR-7,TSR-8,TSR-6,TSR-9 | ASIL D |
| CREQ-115372 | OS shall allow usage of exported services from trusted applications before start of the OS. | TSR-7 | ASIL D |
| CREQ-105586 | OS shall provide a service to call exported services from non-trusted applications. | TSR-7,TSR-6,TSR-8,TSR-9 | ASIL D |
| CREQ-105587 | OS shall allow usage of exported services from non-trusted applications before start of the OS. | TSR-7 | ASIL D |
| CREQ-253949 | OS shall provide a service to call lightweight exported services from trusted applications. | TSR-7,TSR-9,TSR-6,TSR-8 | ASIL D |
| CREQ-253950 | OS shall allow usage of lightweight exported services from trusted applications before start of the OS. | TSR-7 | ASIL D |
| CREQ-48 | OS shall provide an application specific callback during OS startup. | TSR-6,TSR-1 | ASIL D |
| CREQ-76 | OS shall provide an application specific callback during OS shutdown. | TSR-6 | ASIL D |
| CREQ-54 | OS shall provide an application specific callback if an error occurs. | TSR-6 | ASIL D |
| CREQ-844 | OS shall provide global memory protection configuration. | TSR-7 | ASIL D |
| CREQ-41 | OS shall provide memory protection configuration for applications. | TSR-7 | ASIL D |
| CREQ-62 | OS shall provide memory protection configuration for tasks and category 2 ISRs. | TSR-7 | ASIL D |
| CREQ-73 | OS shall provide a service to return the access rights of a memory access of a task. | TSR-6,TSR-7 | ASIL D |
| CREQ-13 | OS shall provide a service to return the access rights of a memory access of a category 2 ISR. | TSR-7,TSR-6 | ASIL D |
| CREQ-49 | OS shall provide execution time protection. | TSR-8 | ASIL D |
| CREQ-85 | OS shall provide inter-arrival time protection. | TSR-8 | ASIL D |
| CREQ-31 | OS shall provide locking time protection. | TSR-8 | ASIL D |
| CREQ-845 | OS shall monitor execution times. | TSR-8 | ASIL D |
| CREQ-846 | OS shall monitor inter arrival time frames. | TSR-8 | ASIL D |
| CREQ-847 | OS shall monitor locking times. | TSR-8 | ASIL D |
| CREQ-40 | OS shall prevent OS-Applications from corrupting the OS through service calls. | TSR-6,TSR-7 | ASIL D |
| CREQ-131 | OS shall provide peripheral regions. | TSR-7 | ASIL D |
| CREQ-35 | OS shall provide a service to modify a value in a peripheral region. | TSR-7,TSR-6 | ASIL D |
| CREQ-79 | OS shall provide a service to read a value from a peripheral region. | TSR-6,TSR-7 | ASIL D |
| CREQ-145 | OS shall provide a service to write a value in a peripheral region. | TSR-6,TSR-7 | ASIL D |
| CREQ-115373 | OS shall allow usage of services for peripheral regions before start of the OS. | TSR-7 | ASIL D |
| CREQ-88 | OS shall provide a stack monitoring mechanism. | TSR-7,TSR-6 | ASIL D |
| CREQ-26 | OS shall be able to call a global callback function if an error occurs. | TSR-6 | ASIL D |
| CREQ-38 | OS shall be able to call a global callback function if a fatal error occurs. | TSR-9,TSR-8,TSR-6 | ASIL D |
| CREQ-133061 | OS shall be able to call a global callback function if an internal error occurs. | TSR-6 | ASIL D |
| CREQ-97 | OS shall provide a service to all configured error callbacks, which return the parameters of the system service which triggered error handling. | TSR-6 | ASIL D |
| CREQ-23 | OS shall provide a service to all configured error callbacks, which returns the service identifier where the error has been risen. | TSR-101876,TSR-6 | ASIL D |
| CREQ-102 | OS shall provide information to determine the service and the cause of a reported error. | TSR-101876,TSR-6 | ASIL D |
| CREQ-129663 | OS shall provide a service, which writes the context of the thread to which the system returns after error handling. | TSR-6 | ASIL D |
| CREQ-129664 | OS shall provide a service, which returns the context of the thread which triggered a fatal error. | TSR-6 | ASIL D |
| CREQ-247263 | OS shall provide a service, which returns the address of the latest instruction that caused a fatal error. | TSR-6 | ASIL D |
| CREQ-70 | OS shall provide a service to forcibly terminate a task. | TSR-9,TSR-6 | ASIL D |
| CREQ-21 | OS shall provide a service to forcibly terminate a category 2 ISR. | TSR-9,TSR-6 | ASIL D |
| CREQ-168 | OS shall provide a service to select the idle mode action. | TSR-6 | ASIL D |
| CREQ-75 | OS shall provide inter-application communication. | TSR-12,TSR-7 | ASIL D |
| CREQ-848 | OS IOC shall provide queued communication. | TSR-12,TSR-6,TSR-7 | ASIL D |
| CREQ-849 | OS IOC shall provide unqueued communication. | TSR-7,TSR-12 | ASIL D |
| CREQ-850 | OS IOC shall provide 1:1 communication. | TSR-12,TSR-7 | ASIL D |
| CREQ-852 | OS IOC shall provide N:1 communication. | TSR-7,TSR-12 | ASIL D |
| CREQ-851 | OS IOC shall provide N:M communication. | TSR-7,TSR-12 | ASIL D |
| CREQ-150 | OS shall provide a service to write data to an unqueued IOC channel. | TSR-6,TSR-7,TSR-12 | ASIL D |
| CREQ-55 | OS shall provide a service to read data from a unqueued IOC channel. | TSR-7,TSR-6,TSR-12 | ASIL D |
| CREQ-91 | OS shall provide a service to send data to a queued IOC channel. | TSR-7,TSR-6,TSR-12 | ASIL D |
| CREQ-160 | OS shall provide a service to receive data from a queued IOC channel. | TSR-12,TSR-6,TSR-7 | ASIL D |
| CREQ-90 | OS shall provide a service to write multiple data to an unqueued IOC channel. | TSR-7,TSR-6,TSR-12 | ASIL D |
| CREQ-147 | OS shall provide a service to read multiple data from an unqueued IOC channel. | TSR-7,TSR-6,TSR-12 | ASIL D |
| CREQ-119 | OS shall provide a service to send multiple data to a queued IOC channel. | TSR-6,TSR-7,TSR-12 | ASIL D |
| CREQ-113 | OS shall service a method to receive multiple data from a queued IOC channel. | TSR-12,TSR-7,TSR-6 | ASIL D |
| CREQ-128 | OS shall provide a service to clear all data from a queued IOC channel. | TSR-7,TSR-12,TSR-6 | ASIL D |
| CREQ-141 | OS shall be able to call a callback function upon IOC data reception. | TSR-12,TSR-7,TSR-6 | ASIL D |
| CREQ-124 | OS shall schedule tasks based on priorities. | TSR-6,TSR-8 | ASIL D |
| CREQ-86 | OS shall provide full preemptive task scheduling. | TSR-8,TSR-6 | ASIL D |
| CREQ-30 | OS shall provide non preemptive task scheduling. | TSR-8,TSR-6 | ASIL D |
| CREQ-229342 | OS shall provide round robin scheduling. | TSR-6 | ASIL D |
| CREQ-149 | OS shall provide a service to identify the local core. | TSR-6 | ASIL D |
| CREQ-148 | OS shall provide a service to get the number of cores controlled by OS. | TSR-6 | ASIL D |
| CREQ-37 | OS shall provide a service to start a core for usage of AUTOSAR OS software. | TSR-1,TSR-7,TSR-8,TSR-9,TSR-12,TSR-6 | ASIL D |
| CREQ-120 | OS shall provide a service to start a core for usage of non AUTOSAR OS software. | TSR-1,TSR-6 | ASIL D |
| CREQ-115996 | OS shall be able to initialize itself and the hardware on any of the available cores. | TSR-1 | ASIL D |
| CREQ-213720 | OS shall provide a service to get the start state of a core. | TSR-6 | ASIL D |
| CREQ-130 | OS shall allow to share stacks between tasks which do not preempt each other. | TSR-7 | ASIL D |
| CREQ-115010 | OS shall provide a callback for signalling a task activation. | TSR-6 | ASIL D |
| CREQ-115028 | OS shall provide a callback for signalling the setting of an event. | TSR-6 | ASIL D |
| CREQ-115029 | OS shall provide a callback for signalling a thread switch. | TSR-6 | ASIL D |
| CREQ-115030 | OS shall provide a callback for signalling forcible termination of a thread. | TSR-6 | ASIL D |
| CREQ-115031 | OS shall provide a callback for signalling the acquirement of a resource. | TSR-6 | ASIL D |
| CREQ-115032 | OS shall provide a callback for signalling the release of a resource. | TSR-6 | ASIL D |
| CREQ-115033 | OS shall provide a callback for signalling the attempt to acquire a spinlock. | TSR-6 | ASIL D |
| CREQ-115034 | OS shall provide a callback for signalling the acquirement of a spinlock. | TSR-6 | ASIL D |
| CREQ-115035 | OS shall provide a callback for signalling the release of a spinlock. | TSR-6 | ASIL D |
| CREQ-115036 | OS shall provide a callback for signalling the attempt to internally acquire a spinlock. | TSR-6 | ASIL D |
| CREQ-115037 | OS shall provide a callback for signalling the internal acquirement of a spinlock. | TSR-6 | ASIL D |
| CREQ-115038 | OS shall provide a callback for signalling the internal release of a spinlock. | TSR-6 | ASIL D |
| CREQ-115039 | OS shall provide a callback for signalling the locking of interrupts. | TSR-6 | ASIL D |
| CREQ-115040 | OS shall provide a callback for signalling the release of an interrupt lock. | TSR-6 | ASIL D |
| CREQ-140268 | OS shall provide a callback for signalling failed task activation because the number of activations exceeds the limit. | TSR-6 | ASIL D |
| CREQ-140269 | OS shall provide a callback for signalling that event is already set when WaitEvent is called. | TSR-6 | ASIL D |
| CREQ-Os-ArtiServiceCall | OS shall provide ARTI callbacks for the class OS_SERVICECALLS. | TSR-6,TSR-7 | ASIL D |
| CREQ-Os-ArtiTask | OS shall provide ARTI callbacks for the class OSARTI_TASK. | TSR-6,TSR-7 | ASIL D |
| CREQ-Os-ArtiCat2Isr | OS shall provide ARTI callbacks for the class OS_CAT2ISR. | TSR-6,TSR-7 | ASIL D |
| CREQ-Os-ArtiSpinlock | OS shall provide ARTI callbacks for the class OS_SPINLOCK. | TSR-6,TSR-7 | ASIL D |
| CREQ-Os-ArtiApplication | OS shall provide ARTI callbacks for the class OS_APPLICATION. | TSR-6,TSR-7 | ASIL D |
| CREQ-Os-ArtiProtectionHook | OS shall provide ARTI callbacks for the class OS_PROTECTIONHOOK. | TSR-6,TSR-7 | ASIL D |
| CREQ-300 | OS shall provide the state READY for tasks. | TSR-8,TSR-6 | ASIL D |
| CREQ-302 | OS shall provide the state RUNNING for tasks. | TSR-8,TSR-6 | ASIL D |
| CREQ-303 | OS shall provide the state SUSPENDED for tasks. | TSR-8,TSR-6 | ASIL D |
| CREQ-301 | OS shall provide the state WAITING for Tasks. | TSR-8,TSR-6 | ASIL D |
| CREQ-305 | OS shall provide the state SCHEDULETABLE_NEXT for schedule tables. | TSR-8 | ASIL D |
| CREQ-308 | OS shall provide the state SCHEDULETABLE_STOPPED for schedule tables. | TSR-8 | ASIL D |
| CREQ-309 | OS shall provide the state SCHEDULETABLE_WAITING for schedule tables. | TSR-8 | ASIL D |
| CREQ-310 | OS shall provide the state SCHEDULETABLE_RUNNING for schedule tables. | TSR-8 | ASIL D |
| CREQ-311 | OS shall provide the state SCHEDULETABLE_RUNNING_AND_SYNCHRONOUS for schedule tables. | TSR-8 | ASIL D |
| CREQ-1263 | OS shall provide the state APPLICATION_ACCESSIBLE for applications. | TSR-8,TSR-7,TSR-6 | ASIL D |
| CREQ-1264 | OS shall provide the state APPLICATION_RESTARTING for applications. | TSR-9,TSR-7,TSR-8,TSR-6 | ASIL D |
| CREQ-1265 | OS shall provide the state APPLICATION_TERMINATED for applications. | TSR-9,TSR-7,TSR-6,TSR-8 | ASIL D |
| CREQ-1201 | OS shall be executable on any combination of cores provided by the hardware. | TSR-7,TSR-12,TSR-1,TSR-4,TSR-8,TSR-9 | ASIL D |
This component in addition to the assumed safety requirements ensures freedom from interference with respect to memory and timing with up to ASIL D.
- ForeignTraceId: SMI-1259
- ForeignAlternativeId: SMI-113E73C8-1FDD-4750-B87B-D295C80A77FC
- ObjectType: RQM_SAFETY_MANUAL_ITEM

### 6ffcfc891a9a949edce6068b2d61b8b32f276bc0c1d8768e14687cea065cd284: Configuration constraints
- ChapterNumber: 9.2
- ObjectType: DocItem

#### b3a31ca4548a0d0e5c7174d2131dcf278fe7ce41b6b6e22910010bffec07ac49
The user of MICROSAR Safe shall configure and verify the extended OS status of APIs.
The attribute /MICROSAR/Os_Core/Os/OsOs/OsStatus shall be equal to EXTENDED.
The OS safety measures rely on the validity checks defined for EXTENDED status of OS API calls. Without these checks invalid calls might destroy the system integrity and violate safety requirements. Ensuring the validity of API calls and arguments in STANDARD status for any caller (which e.g. might be QM software) is considered to be infeasible.
The user does not need to check this setting explicitly, as the MICROSAR Safe Silence Verifier (MSSV) assures that this setting is correct.
- ForeignTraceId: SMI-378
- ForeignAlternativeId: SMI-BC677F67-2C4F-473B-919F-57C6ABAE0AAC
- ObjectType: RQM_SAFETY_MANUAL_ITEM

#### dd034c32bcf3949dee6b5b13cf3981b3e3c8f100b5ab940af43a3807426da807
The user of MICROSAR Safe shall configure and verify the service protection.
The attribute /MICROSAR/Os_Core/Os/OsOs/OsServiceProtection shall be equal to TRUE.
The OS safety measures rely on the validity checks defined for OsServiceProtection. Without these checks, invalid API calls might destroy the system integrity and violate safety requirements. Ensuring the validity of API calls for each caller (which might be QM software) is not considered feasible if OsServiceProtection is disabled.
The user does not need to check this setting explicitly, as the MICROSAR Safe Silence Verifier (MSSV) assures that this setting is correct.
- ForeignTraceId: SMI-377
- ForeignAlternativeId: SMI-1640C9BE-BFBF-4F7C-BBF1-A8EEFD81F311
- ObjectType: RQM_SAFETY_MANUAL_ITEM

#### d8fa0197703d7aa3e4ca37156552dcbab7b5688baa5fbfe1f92563494ee5ae0a
The user of MICROSAR Safe shall configure and verify the scalability class 3 or 4.
The attribute /MICROSAR/Os_Core/Os/OsOs/OsScalabilityClass shall be equal to SC3 or SC4.
The OS safety measures rely on memory protection and service protection provided by the scalability classes SC3 and SC4. Without memory protection, all software parts (even QM parts) would have to ensure freedom from interference regarding memory (including absence of stack overflow). Without service protection, all software parts (even QM parts) would have to ensure only calls with valid access rights.
The user does not need to check this setting explicitly, as the MICROSAR Safe Silence Verifier (MSSV) assures that this setting is correct.
- ForeignTraceId: SMI-379
- ForeignAlternativeId: SMI-FB4E2EE1-AC92-4EEF-9B64-A722899D57FA
- ObjectType: RQM_SAFETY_MANUAL_ITEM

#### d640a594733e3191983d7f53f59df37e5ebba6388429479ed2012df4bf84c67b
The user of MICROSAR Safe shall not use ISRs of category 1 if timing protection is configured.
If a thread is killed because of timing protection, ISRs of category 1 might be aborted.
A possible workaround is to use ISRs of category 2 instead of category 1.
- ForeignTraceId: SMI-385
- ForeignAlternativeId: SMI-2BC4CEFD-C6C0-4A93-A79E-90B47DE0838C
- ObjectType: RQM_SAFETY_MANUAL_ITEM

### 4d98d752f1e2cd42e8a4ce744956c0f7670ac82cce590b96536b330fbf14deed: Additional verification measures
- ChapterNumber: 9.3
- ObjectType: DocItem

#### 6e532665c120c7b001bdb0562dd866735584e012331e8c3141d8e261677ab40d
The user of MICROSAR Safe shall ensure the correct usage of the OS regarding program flow. The correct program flow is only ensured if all OS API functions fulfill the expectations of the user application designer and are used correctly according to the AUTOSAR OS specification and the technical reference.
This requirement is fulfilled by all MICROSAR Safe components. It only applies if APIs of the operating system are used directly by the user of MICROSAR Safe.
This may be checked by monitoring the program flow at development time. Another measure may be, to check whether the API functions have the expected effects by double checking the technical reference.
- ForeignTraceId: SMI-380
- ForeignAlternativeId: SMI-2339ABE8-9071-4FFB-94B6-234BC523200E
- ObjectType: RQM_SAFETY_MANUAL_ITEM

#### 0bffa8c288db7ac802d22c0a38ff6263c9e84772a380e92acc10066547d8f032
The user of MICROSAR Safe shall ensure the correct usage of the hardware peripherals.
It is assumed that user software uses the microcontroller exactly as specified in the vendors hardware documentation. Hardware peripheral access may be performed using the MICROSAR OS Peripheral Access APIs.
- ForeignTraceId: SMI-3732
- ForeignAlternativeId: SMI-C251C7C7-3C75-46A9-B2C8-84810A0B1B22
- ObjectType: RQM_SAFETY_MANUAL_ITEM

#### 0fdcb5faf2475822107c393cfbd3461df0c5d870b5a9dd793a58ef9001aa9622
The user of MICROSAR Safe shall not call OS hook functions directly. The OS hook functions shall be called by the OS only. This applies to the following hook functions:
- StartupHook
- ShutdownHook
- ProtectionHook
- PreTaskHook
- PostTaskHook
- ErrorHook
- PanicHook
The OS makes assumptions which are valid if these hook functions are called by the OS. These assumptions might be violated if hook functions are called directly by the user. As a hook may expect that it is called from a specific context, hooks shall not be called from user code directly.
- ForeignTraceId: SMI-383
- ForeignAlternativeId: SMI-5B7B3C76-8B32-473B-B1E8-B0D6528721EC
- ObjectType: RQM_SAFETY_MANUAL_ITEM

#### 2f87b01629f18ef8a1509b90af06d9881d83f02edfff96da31655e18d541a286
The user of MICROSAR Safe shall verify that the context described in the Hardware Software Interface (HSI) of the used platform is sufficient for the requirements of his application. The context is derived from the EABI of the platform as well as the calling conventions of the compiler. Discrepancies may occur in case a coprocessor is used, assembler code uses additional registers or precompiled libraries use different registers.
- ForeignTraceId: SMI-1047
- ForeignAlternativeId: SMI-52D8B360-E152-4C6C-8185-6494724B5DC4
- ObjectType: RQM_SAFETY_MANUAL_ITEM

#### 6b5d93b46a024c79ad8fbde560089a3cb7e0c1beddc96d41324cd623fd0214e8
The user of MICROSAR Safe shall assure that the application initializes the user controlled processor state bits before Os_Init(). The user controlled processor state bits are transfered into every new context as a copy from the previous context. Changing the user controlled processor state bits during runtime may lead to unexpected behavior of the system.
The technical reference of the platform describes all processor state bits controlled by the OS. All other bits are either under user or hardware control. Refer to the hardware manual for a detailed description.
- ForeignTraceId: SMI-100816
- ForeignAlternativeId: SMI-1FC38223-B2F8-4969-9306-783177C4AF8F
- ObjectType: RQM_SAFETY_MANUAL_ITEM

#### 250b67a1a1808f0eea7bccc71afe872652cde36d4c2818769c717ab3f90ba3fc
The user of MICROSAR Safe shall verify that software, which implements safety functionality, shall not rely on functionality provided by the following APIs:
- Os_GetVersionInfo
- Stack Usage API (Os_Get*StackUsage)
- Os_InitInterruptOnly
- ForeignTraceId: SMI-592
- ForeignAlternativeId: SMI-A8F0102D-DA18-4B22-AAD4-1B9C01CBC02B
- ObjectType: RQM_SAFETY_MANUAL_ITEM

#### b4d4d0eb7ce85a4ae79e1ee0c2108d802cbd246ebeddfe1aca88ce8e7218abaa
- ObjectType: DocItem

#### 9e516306e7e53d81b2778cbaeae2d1b81435b9943117a2d84f262e4f117f9b09: Interrupt handling
- ChapterNumber: 9.3.1
- ObjectType: DocItem

##### f13c74f7fc01bec1fde5387b8436f72f2b92b5f35a7594304ab6c2feecd54799
The user of MICROSAR Safe shall ensure the correct usage of the OS regarding interrupt disabling. Unintended disabling of interrupts may lead to timing inconsistencies because pending interrupts might be delayed.
The following interrupt disabling API functions shall be used correctly according to the AUTOSAR OS specification:
- DisableAllInterrupts
- SuspendAllInterrupts
- SuspendOSInterrupts
The user shall select the function that is in accordance to the system design expectations.
- ForeignTraceId: SMI-381
- ForeignAlternativeId: SMI-FA55A18B-4DFA-4846-8626-9F1B33213642
- ObjectType: RQM_SAFETY_MANUAL_ITEM

##### 1545b8ae087d4f526e55f6ed717037202b5f65c0d90586e46d36c85b613c4b03
The user of MICROSAR Safe shall ensure the correct usage of the OS regarding interrupt enabling. Unintended enabling of interrupts may lead to timing inconsistencies (because interrupts, which should be disabled, might occure) and data inconsistencies (see also SMI-11).
The following interrupt enabling API functions shall be used correctly according to the AUTOSAR OS specification:
- EnableAllInterrupts
- ResumeAllInterrupts
- ResumeOSInterrupts
The user shall select the function that is in accordance to the system design expectations.
- ForeignTraceId: SMI-382
- ForeignAlternativeId: SMI-843F75A2-8785-4773-BC81-7FF4D62978D8
- ObjectType: RQM_SAFETY_MANUAL_ITEM

##### 382cfeaf593cbfb8e7d8f4e2952bc24cb8a804bc71e6be6a588e1307b04a7a45
The user of MICROSAR Safe shall verify that the following API functions:
- Os_DisableLevel[KM|UM|AM]
- Os_EnableLevel[KM|UM|AM]
- Os_DisableGlobal[KM|UM|AM]
- Os_EnableGlobal[KM|UM|AM]
are never called in the following cases:
- within critical sections
- nested within other interrupt APIs
- within a section where an interrupt resource is locked
- within interrupt locking spinlocks
- within ISRs, Hook functions, non-trusted functions, trusted functions and alarm callbacks
Furthermore, the disable functions shall only be called when the interrupts are enabled.
- ForeignTraceId: SMI-482
- ForeignAlternativeId: SMI-84F83C4B-A433-4F81-9FBC-DFE67AE2F99C
- ObjectType: RQM_SAFETY_MANUAL_ITEM

##### 6ca2d8e798bcf11025c0a61414fde7f52725ab21b86caf405cc6dd01fe232ca6
The user of MICROSAR Safe shall verify that the following API functions are only called from privileged mode:
- Os_DisableLevelKM
- Os_EnableLevelKM
- Os_DisableGlobalKM
- Os_EnableGlobalKM
- ForeignTraceId: SMI-488
- ForeignAlternativeId: SMI-F8076FD9-FA18-4A5B-B0CC-57BBA2718DA2
- ObjectType: RQM_SAFETY_MANUAL_ITEM

##### ff8841966b77fefaa1dcabec558f9a5e0180960048b8dcb71ab1a7160a97b5df
The user of MICROSAR Safe shall verify that the API functions Os_EnableGlobal[KM|UM|AM] are only called if interrupts were disabled previously by calling the corresponding Os_DisableGlobal[KM|UM|AM] function.
- ForeignTraceId: SMI-489
- ForeignAlternativeId: SMI-26F0DC1B-B545-4261-A1BA-3E002E8B3BA3
- ObjectType: RQM_SAFETY_MANUAL_ITEM

##### 2822e81f000ea228157275eb7a538468858835332f6759e71928e8d88c8ceb28
The user of MICROSAR Safe shall verify that the API functions Os_EnableLevel[KM|UM|AM] are only called if interrupts were disabled previously by calling the corresponding Os_DisableLevel[KM|UM|AM] function.
- ForeignTraceId: SMI-490
- ForeignAlternativeId: SMI-D1A6DD03-9558-460F-9F0D-EEF99C150CEC
- ObjectType: RQM_SAFETY_MANUAL_ITEM

##### 8e18462a65de45930ccb0bb639073c91bd60266df91f355e88f00280fad183a6
The user of MICROSAR Safe shall verify that all APIs called in ISRs of category 0 are allowed to be called in this context by the technical reference.
The call context „inside category 0 ISR“ cannot be checked by the API functions. Erroneous calls are not detected.
- ForeignTraceId: SMI-44677
- ForeignAlternativeId: SMI-98107C77-0ADE-47C4-9752-8B0CDBA1C1E0
- ObjectType: RQM_SAFETY_MANUAL_ITEM

##### a8037aedc8b71a3f33981c4b7f046e1c1e8294d6418a23d737f82c8314e3b7b6
The user of MICROSAR Safe shall verify that all APIs called in ISRs of category 1 are allowed to be called in this context by the AUTOSAR specification and the technical reference.
The call context „inside category 1 ISR“ cannot be checked by the API functions. Erroneous calls are not detected.
- ForeignTraceId: SMI-590
- ForeignAlternativeId: SMI-FF74E306-9838-419B-A151-D8497673E6C9
- ObjectType: RQM_SAFETY_MANUAL_ITEM

##### b254078812bbb6feebfb15f71f3e87b7895a601cc3f763c9124db6f9285e1775
The user of MICROSAR Safe shall verify that all ISRs of category 0 are implemented transparent. Transparent means, that the execution of a category 0 interrupt can not be detected by the OS. Thus, the user has to ensure, that the context described in the HSI of the platform remains unchanged or is restored correctly after the execution of a category 0 ISR.
- ForeignTraceId: SMI-44676
- ForeignAlternativeId: SMI-A2E584A9-2103-4234-904B-68F934618F83
- ObjectType: RQM_SAFETY_MANUAL_ITEM

##### 174c98570f7acad0585cb9f708c9738cde49666b0aa1ed7a6c6f0aa9e6b79027
The user of MICROSAR Safe shall verify that all ISRs of category 1 are implemented transparent. Transparent means, that the execution of a category 1 interrupt can not be detected by the OS. Thus, the user has to ensure, that the context described in the HSI of the platform remains unchanged or is restored correctly after the execution of a category 1 ISR.
- ForeignTraceId: SMI-541
- ForeignAlternativeId: SMI-ED5E26A3-DD37-4F15-A8C0-1B4D3D81B860
- ObjectType: RQM_SAFETY_MANUAL_ITEM

##### 07d60eba51b1cfa1a4fc627167b7ac680185c85b8e8ca74c0849123b0e98bde4
The user of MICROSAR Safe shall verify the functionality of each configured ISR.
This includes the call of the correct ISR handler with the expected priority. In case that the following APIs are used, the user has to check that the correct ISR is influenced.
- Os_InitialEnableInterruptSources
- Os_EnableInterruptSource
- Os_DisableInterruptSource
- Os_ClearPendingInterrupt
The aim of the check is to make sure, that no interrupt sources or vectors are mixed up. Therefore, it is sufficient to perform the check with one of the mentioned functions for each ISR.
- ForeignTraceId: SMI-491
- ForeignAlternativeId: SMI-8FC8592B-8D62-42B7-97FA-2676288836C3
- ObjectType: RQM_SAFETY_MANUAL_ITEM

##### f95920c8fbfcd17d4c5c3a68b09df47bd228998c130934aab199a1e381ff7a52
The user of MICROSAR Safe shall avoid forcible termination by means of the protection reaction of the ProtectionHook in case category 0 ISRs are configured.
If a category 0 ISR causes the ProtectionHook call, the interrupted Task or ISR would be terminated together with the category 0 ISR.
This situation should be handled safely in the application design.
- ForeignTraceId: SMI-44675
- ForeignAlternativeId: SMI-18B0D655-947B-446E-B7BC-98CA62F93CDE
- ObjectType: RQM_SAFETY_MANUAL_ITEM

##### 560793ac3f0507173c5321cabb3ad97a818574e2b396897cebec30cf4c080ed9
The user of MICROSAR Safe shall avoid forcible termination by means of the protection reaction of the ProtectionHook in case category 1 ISRs are configured.
If a category 1 ISR causes the ProtectionHook call, the interrupted Task or ISR would be terminated together with the category 1 ISR.
This situation should be handled safely in the application design.
- ForeignTraceId: SMI-44678
- ForeignAlternativeId: SMI-3B2363D8-E002-442E-99BA-7C1A2CB37BDC
- ObjectType: RQM_SAFETY_MANUAL_ITEM

##### 57b861c8e290e8f6347492ecc6f2e06c5e783315800fe736109fef94c95f8bca
The user of MICROSAR Safe shall be aware that category 0 ISRs cannot be disabled or suspended by the OS interrupt APIs.
The following APIs have no effect on category 0 ISRs:
- DisableAllInterrupts
- EnableAllInterrupts
- SuspendAllInterrupts
- ResumeAllInterrupts
- SuspendOSInterrupts
- ResumeOSInterrupts
- Os_DisableLevelAM
- Os_EnableLevelAM
- Os_DisableLevelKM
- Os_EnableLevelKM
- Os_DisableLevelUM
- Os_EnableLevelUM
- Os_DisableGlobalAM
- Os_EnableGlobalAM
- Os_DisableGlobalKM
- Os_EnableGlobalKM
- Os_DisableGlobalUM
- Os_EnableGlobalUM
The OS provides no measures to ensure data consistency for variables shared between category 0 ISRs and other Tasks or ISRs. Such measures need to be implemented by the user.
- ForeignTraceId: SMI-44681
- ForeignAlternativeId: SMI-67D733F5-B1AC-4EBF-A26D-D539263F2FAC
- ObjectType: RQM_SAFETY_MANUAL_ITEM

##### d19b337baa664b8685eaf21c1b4557b01f960bd9f3d1bf16454dfab598a20921
The user of MICROSAR Safe shall verify that the time between two high resolution timer interrupts is sufficiently small.
In case of a timer of at least 32 bits, the time must not be bigger than 2,147,483,647 hardware ticks.
In case of a timer with less then 32 bits, the time must not be bigger than 2^(n-1) - 1 hardware ticks, where n is the register bit width of the hardware timer module.
Timer interrupts can be delayed by disabling or suspending the interrupt handling or by other interrupts with higher priority.
High resolution timer interrupts are used as Timing Protection interrupts. Additionally, they are used for OS Counters which have the high resolution timer flag enabled.
- ForeignTraceId: SMI-334973
- ForeignAlternativeId: SMI-CDBC7353-1314-42B4-82EF-6BEA340FB303
- ObjectType: RQM_SAFETY_MANUAL_ITEM

#### 71b4973e50997718913d05306e5389183f313b4f376d0988a35169242bac3e28: Memory mapping and linking
- ChapterNumber: 9.3.2
- ObjectType: DocItem

##### 49b7263566b9d8cbed747df881034e2752b26234b31586a3181afb37ae1ff983
The user of MICROSAR Safe shall verify that the complete range specified by each Os_PeripheralConfigType object in Os_Peripheral_Lcfg.c is intended to be accessed by the (non-trusted) callers of the peripheral API. The first writable address is denoted as AddressStart and the last writable address is denoted as AddressEnd.
- ForeignTraceId: SMI-340
- ForeignAlternativeId: SMI-42B5315F-8A39-4920-8402-D2547F1CCE2A
- ObjectType: RQM_SAFETY_MANUAL_ITEM

##### 0abbbd868ed9ddcd1fb92b52c22f4ee56654655f241a7506e71c00c8ac8dd5c7
The user of MICROSAR Safe shall verify for IOC functions, that the configured access rights and linker configuration allow only valid callers to write the corresponding IOC data.
Valid callers are the configured sender applications for the corresponding IOC send data structure and the configured receiver applications for the corresponding IOC data structure.
In order to optimize IOC functionality, the OS links the IOC data structures to the sender/receiver application in many cases. In these cases, the user has to ensure, that no other application has write access to this memory section.
In case the IOC data structures are linked to the OS data section, the OS guarantees that only valid senders/receivers can write to the IOC data structure.
The user may find all IOC data structures in the generated file Os_Ioc_Lcfg.c as dynamic objects.
- ForeignTraceId: SMI-494
- ForeignAlternativeId: SMI-8C17D35E-BF19-4C28-A3FC-9B84BD9BAB27
- ObjectType: RQM_SAFETY_MANUAL_ITEM

##### ee8a53fe41cb279e250a43fc6ec1dad86ba78ca620e7de981d7e0cd8b5158e7e
The user of MICROSAR Safe shall ensure by linkage for each optimized spinlock that only intended tasks and ISRs have write access to the corresponding spinlock data (or at least only tasks and ISRs of partitions with the same ASIL levels).
The user of MICROSAR Safe shall verify that no unintended task or ISR has access to data of optimized spinlocks.
- ForeignTraceId: SMI-495
- ForeignAlternativeId: SMI-D15CC31F-675E-4B73-9220-E8A738FB9B87
- ObjectType: RQM_SAFETY_MANUAL_ITEM

##### bdf9f685015b59d7795cba245f87fa121d852b1253ad9ad84c492cd8a2ab65ab
The user of MICROSAR Safe shall verify that no configured MPU region grants write access to OS variables from non-trusted software.
- ForeignTraceId: SMI-539
- ForeignAlternativeId: SMI-6AAF6A8D-1D62-4BB9-A930-FA902007AA76
- ObjectType: RQM_SAFETY_MANUAL_ITEM

##### ef0796bfb1c8dad71d00b1e5297953394c1bb3e8e539b1a18107f802859ef59c
The user of MICROSAR Safe shall verify that none of the configured MPU regions grants write access to a memory section where OS stacks are linked to. To fulfill this requirement, the generated map file may be helpful.
- ForeignTraceId: SMI-549
- ForeignAlternativeId: SMI-9E100ED0-B7D0-4441-9A8F-5F2B42CEFB2B
- ObjectType: RQM_SAFETY_MANUAL_ITEM

##### 1d81d59cb43978bfde236867c3de37f2f113557329bb8af923c2a8e48b3fbd91
The user of MICROSAR Safe shall verify that the linkage scheme includes a stack safety gap linked adjacent to the stack section (in dependency of the stack growth direction, see technical reference). No software parts shall have write access to the stack safety gap.
This measure allows the MPU to detect stack overflows even if the owner of the stack has write access to data linked adjacent to the stack section.
- ForeignTraceId: SMI-1045
- ForeignAlternativeId: SMI-554B4275-5000-4BA6-AB0A-ECD4926828C3
- ObjectType: RQM_SAFETY_MANUAL_ITEM

##### b7a0ff336d8378d3b55c7f75088d5896107ff58a45d0ec805eed5a7db4cac6f6
The user of MICROSAR Safe shall verify the configuration of access rights to sections.
A precondition to this is, that a concept exists, which describes the partitioning of the address range and the access rights to the partitions for different parts of the software.
This can be done by stopping the execution and checking the MPU register values. Dependent on the granularity of the access right configuration, this should be done globally (static MPU regions), for each OS Application or for each Task and each ISR.
- ForeignTraceId: SMI-564
- ForeignAlternativeId: SMI-EAFE55DB-E72D-4F0D-A949-9E65812F8F3F
- ObjectType: RQM_SAFETY_MANUAL_ITEM

##### bd31d260985fd243f6726831971d1e3a0fcdfb40ef137e89107c55b57efafd6e
The user of MICROSAR Safe shall ensure that the whole OS code is linked within OS start and end code labels as described in the technical reference. The start and end labels are generated into the array OsCfg_OsCode_Section<x>. This array may be found in Os_Error_Lcfg.c.
Exceptions which occur in this address range will lead to the safe state of the OS, while other exceptions cause a call of the ProtectionHook.
- ForeignTraceId: SMI-109809
- ForeignAlternativeId: SMI-E8802DA5-4530-4C2D-9B16-64ADAF935C49
- ObjectType: RQM_SAFETY_MANUAL_ITEM

#### 58be18493b1db2e622ee1da9b6d1bb1b093b371e788fbacd93019ea1f1c2cdf4: Stack
- ChapterNumber: 9.3.3
- ObjectType: DocItem

##### 4e40b0b8534f05b8566f28e08004e1df166fe6e29a4db3543fcff9ddd3ffb111
The user of MICROSAR Safe shall ensure that sufficient stack is available for call/execution of StartOS.
StartOS performs some initializations before switching to an internal stack and enabling the memory protection. The active stack at call of StartOS shall provide sufficient space to execute this code. Because the stack consumption depends on the compiler and the compiler options, it is recommended to switch to a stack provided by the OS before calling StartOS and to use the stack usage measurement API of the OS to determine the necessary stack size.
- ForeignTraceId: SMI-565
- ForeignAlternativeId: SMI-1F1B6B48-A9DE-4EB5-A63A-FCF46A3BFB97
- ObjectType: RQM_SAFETY_MANUAL_ITEM

##### 92d2171a5f993e069e6826317caded05eb8d649bf3af1ac92b9a87a138f07a71
If the attribute /MICROSAR/Os/OsOS/OsGenerateMemMap is equal to USERCODE_AND_STACKS_GROUPED_PER_CORE, the user of MICROSAR Safe shall ensure that all configured stack sizes match the MPU granularity and alignment. Otherwise stack protection cannot be ensured.
- ForeignTraceId: SMI-4452
- ForeignAlternativeId: SMI-24DB70AE-EE0A-4237-8275-686582D683CE
- ObjectType: RQM_SAFETY_MANUAL_ITEM

#### a20abad40aa64af3e1f40a8d7ab25cb9c367d3abbf72606de3d31a751a9136c3: Multicore systems with mixed diagnostic coverage capability
- ChapterNumber: 9.3.4
- ObjectType: DocItem

##### 3307ca5e9c25106da7a15ae18a985007159f5e78bbe3b3ffedb8820a562e94d4
The user of MICROSAR Safe shall ensure that frequent cross core API calls from cores with lower diagnostic coverage to cores with higher diagnostic coverage do not interfere with the application design.
Excessive runtime consumption of cores with lower diagnostic coverage shall not prevent cores with higher diagnostic coverage from keeping the timing constraints.
One possible measure is to use timing protection for the X-Signal ISRs. Furthermore, X-Signal Receiver ISRs may be split among different sender cores and provided API functions may be restricted.
- ForeignTraceId: SMI-483
- ForeignAlternativeId: SMI-DF159AFF-79C5-4008-A88F-031872C92D0B
- ObjectType: RQM_SAFETY_MANUAL_ITEM

##### b63ea6efacfa2f68de1eaf44ea9c55f6da8e4a2756aad2683b9675c9e847a938
The user of MICROSAR Safe shall ensure that synchronous cross core API calls from a core with higher diagnostic coverage to a core with lower diagnostic coverage do not violate the safety goals in case the API calls never return.
Synchronous calls block the caller until the return result is received. If, for any reason, a core with lower diagnostic coverage does not return the result or does not return the result in time, the caller has to deal with this situation.
One possible measure is to use asynchronous X-Signal calls.
- ForeignTraceId: SMI-484
- ForeignAlternativeId: SMI-9A5FAF63-4392-4025-821F-7AC84D874E2E
- ObjectType: RQM_SAFETY_MANUAL_ITEM

##### d816690588335cd5105ddcaa00a3adf5b85a70cf3f583692aa581cd841f22d57
The user of MICROSAR Safe shall call ShutdownAllCores only on cores with the highest diagnostic coverage.
- ForeignTraceId: SMI-485
- ForeignAlternativeId: SMI-1F74FFD6-8DE5-4FF1-81AA-1A3F0992363C
- ObjectType: RQM_SAFETY_MANUAL_ITEM

##### b8eecd9bc669186f05d93a7bf8197f00b92882d8eb22372f1c25d69ee796c259
The user of MICROSAR Safe shall note that the ShutdownHook might not be called during Shutdown on multicore systems with mixed diagnostic coverage capability.
Errors caused by cores with lower diagnostic coverage capabilities (data overwrite) might prevent the call of the ShutdownHook by cores with higher diagnostic coverage.
Note that the AUTOSAR OS specification requires a synchronization barrier before the ShutdownHook. If one core does not reach the barrier, no core will reach the ShutdownHook.
- ForeignTraceId: SMI-486
- ForeignAlternativeId: SMI-38BA1B39-EF6E-42FC-B736-F19D8092C2C7
- ObjectType: RQM_SAFETY_MANUAL_ITEM

##### 6222b7733aa2117a6ebc242b7b6e718630e70c8962a1365d45e5d9220db1d938
The user of MICROSAR Safe shall configure and verify that the core with the highest diagnostic coverage initializes the peripheral moduls used by the OS (e.g. MPU, Interrupt Controller).
The attribute /MICROSAR/Os/OsOS/OsHardwareInitCore shall be set to the core reference with the highest diagnostic coverage.
The user of MICROSAR Safe shall ensure, that, if a core with lower diagnostic coverage initializes peripherals or hardware components (like e.g. a system MPU), the core with higher diagnostic coverage does not rely on this initialization.
- ForeignTraceId: SMI-487
- ForeignAlternativeId: SMI-DBFD913D-EC46-4C8B-9581-04D44D01CA61
- ObjectType: RQM_SAFETY_MANUAL_ITEM

##### 9efc0b6e33ce573e73412502f2bbd65a9ca6d36358407237b3c060b575f09647
The user of MICROSAR Safe shall verify that the configuration of cross core API calls prevents cores with lower diagnostic coverage from shutting down cores with higher diagnostic coverage.
Mind that X-Signal Receiver ISRs may be split among different sender cores and provided API functions may be restricted.
- ForeignTraceId: SMI-493
- ForeignAlternativeId: SMI-EC32353B-98E3-43DA-856B-51B386F46D43
- ObjectType: RQM_SAFETY_MANUAL_ITEM

##### c18824f8dc071ff67c7a294417dccfb90bd9360404d7280b0e8b1e0e1c5a60a8
The user of MICROSAR Safe shall ensure that the receiver core of cross core API calls is able to handle unintended calls of APIs. This applies only to APIs which are allowed to be called between two cores by configuration.
- ForeignTraceId: SMI-25766
- ForeignAlternativeId: SMI-1D27DCD1-CB7C-497B-A3D4-8A84164D935D
- ObjectType: RQM_SAFETY_MANUAL_ITEM

#### 86e7f1b132fe005bb4e278cd848c3214d7f3f4308349cbbd83a0f64cbd036559: (Non-)Trusted Functions
- ChapterNumber: 9.3.5
- ObjectType: DocItem

##### c618a66abd595c41bdf9f90d074100b699c38fee96c8bdcfaef183f4efab7a47
The user of MICROSAR Safe shall verify that a trusted, non-trusted or fast trusted function checks the validity of passed arguments before usage.
The caller of CallTrustedFunction, Os_CallNonTrustedFunction or Os_CallFastTrustedFunction might be non-trusted. Therefore, the passed data might also not be trustworthy.
- ForeignTraceId: SMI-497
- ForeignAlternativeId: SMI-E945A453-1A0B-48F1-B6A7-E0C14FA0A647
- ObjectType: RQM_SAFETY_MANUAL_ITEM

##### 21708e24ee9f16e00e5a062ea2c882545e86b1d79368b2ce83ba432503ff9692
The user of MICROSAR Safe shall verify that each caller of a trusted, non-trusted or fast trusted function is allowed to call the function, or the function validates the caller before performing its functionality to prevent from any violation of safety goals.
- ForeignTraceId: SMI-542
- ForeignAlternativeId: SMI-63B7CE2A-B6D9-49E5-871A-686AE2A77556
- ObjectType: RQM_SAFETY_MANUAL_ITEM

##### f342f4fb9bb56a2911213cc0f88524699b0e07ae1b5b0b42f8ea15d8122a6572
The user of MICROSAR Safe shall verify that the caller Task/ISR of each trusted, non-trusted or fast trusted function which uses the FPU, is configured to use the FPU context.
- ForeignTraceId: SMI-95699
- ForeignAlternativeId: SMI-5785376F-31C2-49A2-AAF4-3A81B7149DEA
- ObjectType: RQM_SAFETY_MANUAL_ITEM

#### 9c23075b6e8792802808724914cf258a17df36e0ac9209091c8e2865771fecae: Miscellaneous
- ChapterNumber: 9.3.6
- ObjectType: DocItem

##### 42de3ae2c06094828d17f3661d66ca24aded99e8603bb554f349a03fb0b9a209
The user of MICROSAR Safe shall not rely on the error parameter macros.
These are named: OSError_<API-name>_<parameter-name>().
They are not assumed as safety requirements by Vector.
- ForeignTraceId: SMI-480
- ForeignAlternativeId: SMI-30B8B48E-A4C2-4347-807A-7E87D4A19DCA
- ObjectType: RQM_SAFETY_MANUAL_ITEM

##### 993369ee544800d0fd57c24ef8ac9d50a921065a350f1d5124d2b5cb84f994b8
The user of MICROSAR Safe shall notify that the PanicHook might not be called if the active thread is not allowed to modify the interrupt enable/disable state.
Before calling the PanicHook, the OS disables all interrupts. If this fails, the ProtectionHook might be called, caused by the illegal access (depending on hardware platform).
- ForeignTraceId: SMI-481
- ForeignAlternativeId: SMI-9A9C3EF4-348F-43F0-A8CE-F4C5040A9E7C
- ObjectType: RQM_SAFETY_MANUAL_ITEM

##### 124a8addce3f39b81760943457345bd47df92044d1b90a3ac12d613e6cb17151
The user of MICROSAR Safe shall verify for cross core API calls that for each pair of sender/receiver cores at least one API call is tested and verified across these cores.
The test shall be performed for both directions.
- ForeignTraceId: SMI-492
- ForeignAlternativeId: SMI-BA8191B7-C79D-4357-80AF-3C7859EA5D68
- ObjectType: RQM_SAFETY_MANUAL_ITEM

##### 19c0949b406f5b0988fa3cf669e3b8d80bd300206515da7ce8d91fff515fa17e
The user of MICROSAR Safe shall verify that calls of the optimized spinlock API don’t violate any of the spinlock API constraints (e.g. the order of locking, no simultaneous locks from the same core, allowed caller). The optimized spinlock API skips any checks and therefore does not detect wrong calls.
Mind that the order of GetSpinlock calls also depends on preemption of tasks and ISRs.
- ForeignTraceId: SMI-496
- ForeignAlternativeId: SMI-3CD0DDD3-3436-4724-A956-33516ECBAF0E
- ObjectType: RQM_SAFETY_MANUAL_ITEM

##### 0e3f1b03539bc1eb1fa6e8e6e185620f332913923e326939b0ecee489399d75f
The user of MICROSAR Safe shall verify the correct usage of IOC API functions. These functions don’t call the ErrorHook. It is recommended to check the return code of these functions:
- IocSend/IocWrite
- IocSendGroup/IocWriteGroup
- IocReceive/IocRead
- IocReceiveGroup/IocReadGroup
- ForeignTraceId: SMI-591
- ForeignAlternativeId: SMI-DB82F7E8-B106-4F1D-85C6-4F720A835D25
- ObjectType: RQM_SAFETY_MANUAL_ITEM

##### b5df298e942be8b2ac4a60b4163523daed0db0351c2479ea9489485ad2ce14c5
The user of MICROSAR Safe shall be aware that spinlocks occupied by an IOC channel are not released when the communicating task or ISR is terminated via protection hook.
The operating system does not guarantee that calls to the IOC API for channels, which have blocked spinlocks, will return.
Spinlocks in IOC APIs are, for example, used when
- An IOC channel is non-queued or
- Multiple senders are configured for the same queued channel
- ForeignTraceId: SMI-109842
- ForeignAlternativeId: SMI-78072F7E-7170-43AB-BC7D-0BD16AED8671
- ObjectType: RQM_SAFETY_MANUAL_ITEM

##### 0a172979746bbc40ec6b58e9a529cbd7ccd91031deea1a3186bebb60817de7b7
The user of MICROSAR Safe shall verify that the user software does not contain system call instructions.
Any system call instruction will result in an OS API or in an OS Error. If the user code uses a system call instruction directly, the triggered OS API will most likely not work as expected. Instead, system calls shall only be used by OS APIs.
A possible verification method might be reviewing the code for (inline) assembler statements, pragmas or intrinsic functions containing system call instructions.
System calls used by the OS are described in the technical reference.
- ForeignTraceId: SMI-540
- ForeignAlternativeId: SMI-6ABA3D1C-A384-4085-A3F6-406D89598AA2
- ObjectType: RQM_SAFETY_MANUAL_ITEM

##### ae5a8710ebf2f5e1f1632781126f78955b8b9f9d252be536b606c917a0111595
The user of MICROSAR Safe shall verify that the array OsCfg_CorePhysicalRefs contains all physical cores. The array may be found in Os_Hal_Kernel_Lcfg.c.
For each existing physical hardware core identifier there shall be one corresponding entry inside the array. This entry is indexed by the physical hardware core identifier which is provided directly by the hardware registers.
- ForeignTraceId: SMI-2900
- ForeignAlternativeId: SMI-7FD4E6C2-A328-478B-BB82-5912C8379776
- ObjectType: RQM_SAFETY_MANUAL_ITEM

##### b710a9f837e44c2ee514f47b7b9a598c11c367ead800dcffcabed9af4ba556bb
The user of MICROSAR Safe shall verify that the array OsCfg_Hal_Context_ExceptionContextRef contains all physical cores. The array may be found in Os_Hal_Context_Lcfg.c.
For each existing physical hardware core identifier, which is also an Autosar core, there shall be one corresponding entry (not NULL_PTR) inside the array. This entry is indexed by the physical hardware core identifier which is provided directly by the hardware registers.
- ForeignTraceId: SMI-39288
- ForeignAlternativeId: SMI-03660C11-125E-4E21-AF29-2BF294B29494
- ObjectType: RQM_SAFETY_MANUAL_ITEM

##### fe93349d93e48862b09ecb666bd296f7304bcd66a0c84191ec290794ba30bd3d
The user of MICROSAR Safe shall verify the expected behavior of the system if the following OS APIs are used:
- Os_GetExceptionContext
- Os_SetExceptionContext
The OS is not able to guarantee the correctness of the context structure for each possible situation. Thus, the user of MICROSAR Safe needs to assure the functionality for his use case on his own. For this, the values of the members of the structure Os_ExceptionContextType need to be checked for correctness. In case of Os_SetExceptionContext usage, the register values need to be checked against the values in the context structure after returning. Os_GetExceptionContext usage can be checked by preparing a context, triggering an exception and checking the returned values by a runtime test or with the help of a debugger. For Os_SetExceptionContext a breakpoint may be set to the return address in order to check the restored register values against the values in the context structure.
- ForeignTraceId: SMI-487587
- ForeignAlternativeId: SMI-4D387610-13A0-4327-9529-155811854013
- ObjectType: RQM_SAFETY_MANUAL_ITEM

##### 226ef3c985c79b3d3bc6ddd9a40259b9aad78fa83ef444a598cd5bbbade3d545
The user of MICROSAR Safe shall verify that peripheral APIs
- Os_ReadPeripheral8Legacy
- Os_ReadPeripheral16Legacy
- Os_ReadPeripheral32Legacy
- Os_WritePeripheral8Legacy
- Os_WritePeripheral16Legacy
- Os_WritePeripheral32Legacy
- Os_ModifyPeripheral8Legacy
- Os_ModifyPeripheral16Legacy
- Os_ModifyPeripheral32Legacy
are not used on platforms which address width is greater than 32 bits.
- ForeignTraceId: SMI-44342
- ForeignAlternativeId: SMI-811C1986-5B48-4A5C-B920-60307889DACE
- ObjectType: RQM_SAFETY_MANUAL_ITEM

##### 672cfdd69e6c9e08bea7f63fcd3ccd4606dd654a41334f8d8c022d6288bc29b4
The user shall ensure real time behavior of the system, even in case of delayed calls of the ProtectionHook.
The ProtectionHook may be delayed by the execution of Cat 0 ISRs. So Cat 0 ISRs should either not be used or assure a sufficiently short runtime.
- ForeignTraceId: SMI-44679
- ForeignAlternativeId: SMI-CCA4257F-95C4-45FB-B7B0-FA928CBB4579
- ObjectType: RQM_SAFETY_MANUAL_ITEM

##### 41289735d79bbbf029668d5dbff04291ee10e172bfec3f90c43935d5b7ce6202
The user of MICROSAR Safe shall be aware that in case that MICROSAR OS detects a potentially internal inconsistency, MICROSAR OS enters the PanicHook. The PanicHook is executed with all interrupts disabled. If the PanicHook returns, the OS enters an endless loop with all interrupts disabled. This is assumed to be the safe state of the ECU.
- ForeignTraceId: SMI-109810
- ForeignAlternativeId: SMI-165E7146-15A2-47FB-9156-3DC6851DE193
- ObjectType: RQM_SAFETY_MANUAL_ITEM

##### f94039dac3ae33f0d81bbf4d88fc7a554162f3b0f227f9aedc340fd55aee060f
The user of MICROSAR Safe shall verify that the type Os_AppAccessMaskType is generated in accordance to the number of configured OS Applications and that OS_APPMASK_BITWIDTH is defined in accordance to the processors bit width.
The definition for OS_APPMASK_BITWIDTH may be found in Os_Application_Lcfg.h:
#define OS_APPMASK_BITWIDTH (<BitWidth>u)
The type definition for AppAccessMaskType may be found in Os_Types_Lcfg.h.
If OS_APPID_COUNT is larger than <BitWidth>:
typedef P2CONST(uint<BitWidth>, TYPEDEF, OS_CONST) Os_AppAccessMaskType;
Otherwise:
typedef uint<BitWidth> Os_AppAccessMaskType;
Where <BitWidth> is the bit width of the processor (32 or 64).
- ForeignTraceId: SMI-429122
- ForeignAlternativeId: SMI-69E26772-DAF4-47F5-A081-F5E265470C62
- ObjectType: RQM_SAFETY_MANUAL_ITEM

#### 21cbfdb6f216da1c8ce0b3e57025f75db6107e29f4a085146c2e865caf07cbda: Tracing
- ChapterNumber: 9.3.7
- ObjectType: DocItem

##### 3d08f6b8492b1af65d2b1eef0339c993b5a9922b82265e1debd99f870d5f81be
The user of MICROSAR Safe shall be aware that user timing or ARTI hook implementation influences the runtime behaviour of the system.
- ForeignTraceId: SMI-69754
- ForeignAlternativeId: SMI-106458F0-D5DC-4F56-994A-4FD5F3DE8C8D
- ObjectType: RQM_SAFETY_MANUAL_ITEM

##### 57a532134b10afb3c7a64b5c86708db532cd051027ea4fd2c2a476650b7a5af1
The user of MICROSAR Safe shall not use any OS API within timing or ARTI hooks.
- ForeignTraceId: SMI-69755
- ForeignAlternativeId: SMI-DDEA7F40-9529-47F5-B416-FFDDD17CB44E
- ObjectType: RQM_SAFETY_MANUAL_ITEM

#### 5bbf9eee7745627926952207c6be39e587c213a497732bd0cb44c516a82c61b5: 1.3.8 Barriers
- ObjectType: DocItem

##### 5f94fef544630a24d449153b52e3ca32b629deb0caf3a6ff74713f45e19f624c
The user of MICROSAR Safe shall ensure, that the number of calls to the API Os_BarrierSynchronize is identical for all participating tasks of the referenced barrier.
Otherwise, a participating task may block an entire core, which results in unpredictable behaviour.
- ForeignTraceId: SMI-309405
- ForeignAlternativeId: SMI-7E9658AA-400F-4508-99F3-56D5C1852AC3
- ObjectType: RQM_SAFETY_MANUAL_ITEM

#### 7d5ea19c867bbf327de5899f45e9f27de790be1c20c35569a4d368aff9f88615: Inter OS Application Communication (IOC)
- ChapterNumber: 9.3.9
- ObjectType: DocItem

##### 131353945dd18ada192b16ef00928db86e8b633f84810e163f6dd175c7f27092
This chapter describes the review of the correctness of the locking mode generation in file Os_Ioc_Lcfg.c for all configured senders, writers, receivers and readers of IOC communications. In order to keep each safety manual item sufficiently simple, the review has been split into several items. However, it may make sense, to scan through the file for any sender, writer, receiver or reader configuration structures and to perform the respective review on them. Typically two safety manual items will describe the complete review for a specific sender, writer, receiver or reader. For the receivers of queued IOC communications, only one safety manual item needs to be considered.
- ObjectType: DocItem

##### bcf702b1376ebd1d7583328b5e16f0aacf2c123bd917b7ef2ed7236cf7a9d935
The user of MICROSAR Safe shall verify the consistency of the LockMode and the Spinlock pointer for all generated configuration structures of readers on IOC communications. The configuration data structure of readers in Os_Ioc_Lcfg.c looks like:
CONST(Os_IocReadConfigType, OS_CONST) OsCfg_IocRecv_<NameOfIocCommunication> =


{


/* .Ioc      = */


{


/* .Spinlock              = */ <SpinlockPointer>,


/* .LockMode              = */ <LockModeValue>,


...


/* .AccessingApplications = */ OS_APPID2MASK(<NameOfOsApplication>)


<|OS_APPID2MASK(<NameOfOsApplication>)>*


},


...


};
Where <NameOfIocCommunication> is the configured short name of a container with definition ref: /MICROSAR/Os/OsIoc/OsIocCommunication and <NameOfOsApplication> is the short name of a configuration container, reffered to by the parameter: /MICROSAR/Os/OsIoc/OsIocCommunication/OsIocReceiverProperties/OsIocReceivingOsApplicationRef of the Ioc communication. The values at <SpinlockPointer> and <LockModeValue> shall be reviewed against the table for consistency:
| <LockModeValue> | <SpinlockPointer> |
| --- | --- |
| OS_IOCLOCKMODE_NONE | NULL_PTR |
| OS_IOCLOCKMODE_INTERRUPTS | NULL_PTR |
| OS_IOCLOCKMODE_SPINLOCKS | &OsCfg_Spinlock_IocSpinlock_<NameOfIocCommunication> |
| OS_IOCLOCKMODE_ALL | &OsCfg_Spinlock_IocSpinlock_<NameOfIocCommunication> |
- ForeignTraceId: SMI-889322
- ForeignAlternativeId: SMI-F7964846-C743-4751-BAF6-2B6C60EFB711
- ObjectType: RQM_SAFETY_MANUAL_ITEM

##### cf8cc8f3638d1ce611281e2362d56d081d347820be39bb6e7b04704e19d9a0da
The user of MICROSAR Safe shall verify the consistency of the LockMode and the Spinlock pointer for all generated configuration structures of writers on IOC communications. The configuration structure of writers in Os_Ioc_Lcfg.c looks like:
CONST(Os_IocWriteConfigType, OS_CONST)


OsCfg_IocSend_<NameOfIocCommunication><_<OsIocSenderId>>? =


{


/* .Ioc       = */


{


/* .Spinlock              = */ <SpinlockPointer>,


/* .LockMode              = */ <LockModeValue>,


...


/* .AccessingApplications = */ OS_APPID2MASK(<NameOfOsApplication>)


},


...


};
Where <NameOfIocCommunication> is the configured short name of a container with definition ref: /MICROSAR/Os/OsIoc/OsIocCommunication, <NameOfOsApplication> is the short name of a configuration container, reffered to by the parameter: /MICROSAR/Os/OsIoc/OsIocCommunication/OsIocSenderProperties/OsIocSendingOsApplicationRef and <_<OsIocSenderId>>? is the value of a parameter with definition ref: /MICROSAR/Os/OsIoc/OsIocCommunication/OsIocSenderProperties/OsIocSenderId of that IOC communication. This part of the name may not be available in 1:1 communication as the parameter needs not be configured then. The values at <SpinlockPointer> and <LockModeValue> shall be reviewed against the table for consistency:
| <LockModeValue> | <SpinlockPointer> |
| --- | --- |
| OS_IOCLOCKMODE_NONE | NULL_PTR |
| OS_IOCLOCKMODE_INTERRUPTS | NULL_PTR |
| OS_IOCLOCKMODE_SPINLOCKS | &OsCfg_Spinlock_IocSpinlock_<NameOfIocCommunication> |
| OS_IOCLOCKMODE_ALL | &OsCfg_Spinlock_IocSpinlock_<NameOfIocCommunication> |
- ForeignTraceId: SMI-889323
- ForeignAlternativeId: SMI-BC184977-3476-485C-A406-306FFB700A7B
- ObjectType: RQM_SAFETY_MANUAL_ITEM

##### 2ce69baa12bd7e702effa46ea6635e3ff3cc0890dec4b69d40b1ecf3f55cca61
The user of MICROSAR Safe shall verify the correct generation of the LockMode for all readers and writers of a specific IOC communication. See SMI-889322 and SMI-889323 for the relevant configuration structures. The value for <LockMode> shall be identical for all readers and writers and be in accordance to the table:
| Data can be read/written atomically | Core local and/or Cross-Core communication | <LockMode> |
| --- | --- | --- |
| yes | don't care | OS_IOCLOCKMODE_NONE |
| no | All writer and reader applications are located on the same core. | OS_IOCLOCKMODE_INTERRUPTS |
| no | All writer and reader applications are located on different cores. | OS_IOCLOCKMODE_SPINLOCKS |
| no | Some writer and/or reader applications are located on the same core, while others are located on different cores. | OS_IOCLOCKMODE_ALL |
- ForeignTraceId: SMI-889324
- ForeignAlternativeId: SMI-FB8362E2-3F95-4C00-8CC5-7261A2EB41B3
- ObjectType: RQM_SAFETY_MANUAL_ITEM

##### c3e1bd6ee92186cfabe8accc82aa9ed8d84c7261ae0b971c80223795dbd9ca83
The user of MICROSAR Safe shall verify the consistency of the LockMode and the Spinlock pointer for all generated configuration structures of receivers on IOC communications. The configuration data structure of receivers in Os_Ioc_Lcfg.c looks like:
CONST(Os_Ioc<Bytes>ReceiveConfigType, OS_CONST)


OsCfg_IocRecv_<NameOfIocCommunication> =


{


/* .Ioc      = */


{


/* .Base     = */


{


/* .Spinlock              = */ <SpinlockPointer>,


/* .LockMode              = */ <LockModeValue>,


...


/* .AccessingApplications = */ OS_APPID2MASK(<NameOfOsApplication>)


},


...


},


...


};
Where <NameOfIocCommunication> is the configured short name of a container with definition ref: /MICROSAR/Os/OsIoc/OsIocCommunication. The value of <Bytes> is one of: { 08, 16, 32, Ref }. The value <NameOfOsApplication> is the short name of a configuration container, reffered to by the parameter: /MICROSAR/Os/OsIoc/OsIocCommunication/OsIocReceiverProperties/OsIocReceivingOsApplicationRef of the Ioc communication. The values at <SpinlockPointer> and <LockModeValue> shall be reviewed against the table for consistency:
| <LockModeValue> | <SpinlockPointer> |
| --- | --- |
| OS_IOCLOCKMODE_NONE | NULL_PTR |
| OS_IOCLOCKMODE_INTERRUPTS | NULL_PTR |
| OS_IOCLOCKMODE_SPINLOCKS | &OsCfg_Spinlock_IocSpinlock_<NameOfIocCommunication> |
| OS_IOCLOCKMODE_ALL | &OsCfg_Spinlock_IocSpinlock_<NameOfIocCommunication> |
- ForeignTraceId: SMI-889325
- ForeignAlternativeId: SMI-DB287ABF-2282-4377-BFE9-CA15DB3B5870
- ObjectType: RQM_SAFETY_MANUAL_ITEM

##### 5aa8c1ed66c25578e57f78a0347a154fa3f0e73ea554ef7c55e92cd48c26bdd5
The user of MICROSAR Safe shall verify the consistency of the LockMode and the Spinlock pointer for all generated configuration structures of senders on IOC communications. The configuration structure of senders in Os_Ioc_Lcfg.c looks like:
CONST(Os_Ioc<Bytes>SendConfigType, OS_CONST)


OsCfg_IocSend_<NameOfIocCommunication><_<OsIocSenderId>>? =


{


/* .Ioc       = */


{


/* .Base     = */


{


/* .Spinlock              = */ <SpinlockPointer>,


/* .LockMode              = */ <LockModeValue>,


...


/* .AccessingApplications = */ OS_APPID2MASK(<NameOfOsApplication>)


},


...


},


/* .FifoWrite = */


{


...


/* .Data     = */ <DataBufferPointer>,


...


}


};
Where <NameOfIocCommunication> is the configured short name of a container with definition ref: /MICROSAR/Os/OsIoc/OsIocCommunication and <_<OsIocSenderId>>? is the value of a parameter with definition ref: /MICROSAR/Os/OsIoc/OsIocCommunication/OsIocSenderProperties/OsIocSenderId of that IOC communication. This part of the name may not be available in 1:1 communication as the parameter needs not be configured then. The value of <Bytes> is one of: { 08, 16, 32, Ref }. The value of <NameOfOsApplication> is the short name of a configuration container, reffered to by the parameter: /MICROSAR/Os/OsIoc/OsIocCommunication/OsIocReceiverProperties/OsIocReceivingOsApplicationRef of the Ioc communication. The value of <DataBufferPointer> will be OsCfg_Ioc_<NameOfIocCommunication><_<OsIocSenderId>>?_Buffer_Dyn, where the sender ID may not be identical to the one used for the name of the configuration structure. The values at <SpinlockPointer> and <LockModeValue> shall be reviewed against the table for consistency:
| <LockModeValue> | <SpinlockPointer> |
| --- | --- |
| OS_IOCLOCKMODE_NONE | NULL_PTR |
| OS_IOCLOCKMODE_INTERRUPTS | NULL_PTR |
| OS_IOCLOCKMODE_SPINLOCKS | &OsCfg_Spinlock_IocSpinlock_<NameOfIocCommunication> |
| OS_IOCLOCKMODE_ALL | &OsCfg_Spinlock_IocSpinlock_<NameOfIocCommunication> |
- ForeignTraceId: SMI-889326
- ForeignAlternativeId: SMI-5C94DB88-4595-4A66-AFD8-800AE0D1CE88
- ObjectType: RQM_SAFETY_MANUAL_ITEM

##### a68737d9140677034af8d18ae56764ffe1ea2651bbbb264a70607d34bdc8ea97
The user of MICROSAR Safe shall verify the correct generation of the LockMode for all senders of a specific IOC communication. See SMI-889326 for the relevant configuration structures. The value for <LockMode> shall be identical for all senders and be in accordance to the table:
| More than one sender | <DataBufferPointer> | Core local and/or Cross-Core communication | <LockModeValue> |
| --- | --- | --- | --- |
| no | not relevant | not relevant | OS_IOCLOCKMODE_NONE |
| yes | different for all senders | not relevant | OS_IOCLOCKMODE_NONE |
| yes | Identical for all senders (typically named with lowest sender ID) | All sender applications are located on the same core. | OS_IOCLOCKMODE_INTERRUPTS |
| yes | Identical for all senders (typically named with lowest sender ID) | All sender applications are located on diferent cores. | OS_IOCLOCKMODE_SPINLOCKS |
| yes | Identical for all senders (typically named with lowest sender ID) | Some sender applications are located on the same core while others are located on different core. | OS_IOCLOCKMODE_ALL |
Mind that MICROSAR-OS uses the same data pointer for all sender applications when a receiver callback is configured.
- ForeignTraceId: SMI-889327
- ForeignAlternativeId: SMI-D386C82B-5B77-4C12-B425-68ACCB2268C1
- ObjectType: RQM_SAFETY_MANUAL_ITEM

### ed0904f705e305ca690bddc785c28a6b2c75978da402010392f44b476a0bd04a: Safety requirements required from other components
- ChapterNumber: 9.4
- ObjectType: DocItem

#### 6038b6bb40557a8223898b6652ba83b85d142e97b0bac2f060f308f770b64e75
This component does not require safety requirements from other components.
- ObjectType: DocItem

### 962f926aafcdceaab88675e03c6a2c27ee24718a1c596a66f3aa0f46dbb5f5bd: Dependencies to hardware
- ChapterNumber: 9.5
- ObjectType: DocItem

#### cfed00b834474069b996515fc2341981ca093081032426cfca62039bebeea902
The dependencies of this component to hardware is described in the platform specific part of the Safety Manual.
- ObjectType: DocItem

## d21aabbef95792fbd0b4e3b0e43639627e7cc664a6cd3b7ef6a094aa17941659: Safety Manual Os (ARM CortexM)
- ChapterNumber: 10
- ObjectType: DocItem

### 10c6e034f3ec3b9d966ec6e83da7e6efa6610623c3157657b936fddd12d2d0fa: Assumed safety requirements
- ChapterNumber: 10.1
- ObjectType: DocItem

#### 21692ebda73e81c426d2e06752482eac7df93ed53ecee456097e97f3ba7f94f3
No additional safety requirements are provided.
- ObjectType: DocItem

### b5cf8ed3ab4c2bbf84d290f9acf94c8f365827b7f33bc7913bd5a19d59ddd5e1: Configuration constraints
- ChapterNumber: 10.2
- ObjectType: DocItem

#### 98c5a7da107deee4df31672e33eeb110302bd8968749a947567feef9dbce0ce9
This component does not have configuration constraints.
- ObjectType: DocItem

### dfd9cdf5fa71108c9b4761ae76a9cf143744377d0613208554e6ffd5c296584b: Additional verification measures
- ChapterNumber: 10.3
- ObjectType: DocItem

#### 750a3c25e3dd8588f765f3a6cf4266ce5614835cab955bf3d88a2bc4a300cde7: General
- ChapterNumber: 10.3.1
- ObjectType: DocItem

##### 27fb7fa64606928f8a360f3eaf98b9bf654f6d4aabc6d049031879dbb6d3f3d9
The user of MICROSAR Safe shall verify the generated value of the define OS_HAL_MP_STACK_REGION_NUMBER in Os_Hal_MemoryProtection_Cfg.h. The value must be a valid region number provided by the hardware.
- ForeignTraceId: SMI-44709
- ForeignAlternativeId: SMI-398D1416-05B4-4388-B0B0-878A6DDCEE2F
- ObjectType: RQM_SAFETY_MANUAL_ITEM

##### ec982bf21dbb73f8435353dccc76b9ec4c38d6b6a9d499f4b198eb8158e0aef1
The user of MICROSAR Safe shall verify that the interrupt priority of any Category 2 interrupt (including CounterIsr) that can cause scheduling is lower than all other Category 2 interrupts.
- ForeignTraceId: SMI-394251
- ForeignAlternativeId: SMI-072D3EF3-29FB-4640-A448-A210CA46A51F
- ObjectType: RQM_SAFETY_MANUAL_ITEM

#### b0b87c867854ac12ecb30caff04e8c09b47ed3518fff9be81dfd8c2f7159d01e: ATSAMV7x
- ChapterNumber: 10.3.2
- ObjectType: DocItem

##### c5596e32769a0180af89e7a6d5d729556e527b00efa43aab674ce4a8ee7512d2
The user of MICROSAR Safe shall verify that the array Core2Thread in the object OsCfg_Hal_Core2Thread contains all physical cores.
For each existing physical hardware core identifier there shall be one corresponding entry inside the array which is indexed by the physical hardware core identifier provided directly by the hardware registers.
- ForeignTraceId: SMI-30843
- ForeignAlternativeId: SMI-EFD0D071-8D62-4730-A5D8-054E37159961
- ObjectType: RQM_SAFETY_MANUAL_ITEM

#### 8ed32ee2350c4cd6f1e8f9a73ce8cc84e2c7f032527ea905a6c90cd4d114a040: S32K14x
- ChapterNumber: 10.3.3
- ObjectType: DocItem

##### f2d9b462b2bba460db67ee71f43e91c19b94def48e83edf1829e2e5e09070165
The user of MICROSAR Safe shall verify that the following configuration struct is generated into Os_Hal_Timer_Lcfg.c if the FTM timer is used by the OS:
CONST(Os_Hal_TimerFrtConfigType, OS_CONST) OsCfg_Hal_TimerFrt_<CounterName>
The following struct members must be checked (where <X> (0, 2, 4, 6) is the channel ID) and <y> is the timer module):
ModuleControlRegisterAddress = OS_HAL_TIMER_FTM<Y>_BASE
ModuleCountRegisterAddress = OS_HAL_TIMER_FTM<Y>_BASE + OS_HAL_TIMER_FTM_COUNTREGISTER_OFFSET
ChannelControlRegisterAddress = OS_HAL_TIMER_FTM<Y>_BASE + OS_HAL_TIMER_FTM_CHANNEL<X>_OFFSET
ChannelCompareRegisterAddress = OS_HAL_TIMER_FTM<Y>_BASE + OS_HAL_TIMER_FTM_CHANNEL<X>_OFFSET + OS_HAL_TIMER_FTM_CHANNEL_CMP_OFFSET
- ForeignTraceId: SMI-333241
- ForeignAlternativeId: SMI-69266532-067C-4D69-9886-45A437DC575B
- ObjectType: RQM_SAFETY_MANUAL_ITEM

#### 17143dbd2bde59fb68b1787c7ba2b4f143cf1cad3a81f8c435251fce3d92bd00: S32G274A, S32K3XX and S32R45
- ChapterNumber: 10.3.4
- ObjectType: DocItem

##### 9e841ad4d643a96cabb33a008e785a7656026484f914e5e995cc560e304e25b9
The user of MICROSAR Safe shall verify for all non-autostarted Autosar cores that the generated value of CoreStartAddress has to be the base address of the interrupt vector table of the corresponding core.
The struct "OsCfg_Hal_Core_OsCoreX" shall be checked (where <X> is the logical core ID of the checked core)
CONST(Os_Hal_CoreConfigType, OS_CONST) OsCfg_Hal_Core_OsCoreX = {
/* .CoreId = */ X,
/* .CoreStartAddress = */ (uint32)(&OsCfg_Hal_Core_OsCoreX_VectorTable)
};
- ForeignTraceId: SMI-431712
- ForeignAlternativeId: SMI-9EB6A512-4833-4B69-83B9-EC32D6CA65E8
- ObjectType: RQM_SAFETY_MANUAL_ITEM

#### 7d5673a38e9c1fd29ce84b636581c9929afed4541e88f9622beb73a03f8eaa8e: Traveo II - CYTx
- ChapterNumber: 10.3.5
- ObjectType: DocItem

##### 941ea3b8039db8fcdd3fc70a262cfce4aae850f646c899e9e35f006d68c38f50
The user of MICROSAR Safe shall verify that the following configuration struct is generated into Os_Hal_Timer_Lcfg.c if the TCPWM0 timer is used by the OS:
CONST(Os_Hal_TimerFrtConfigType, OS_CONST) OsCfg_Hal_TimerFrt_<CounterName>
The following struct members must be checked (where <X> is the channel ID):
TimerBaseAddr = OS_HAL_TIMER_FRT_TCPWM0_GROUP2_BASE
CounterIndex = OS_HAL_TCPWM_COUNTER_X
- ForeignTraceId: SMI-568210
- ForeignAlternativeId: SMI-B12D9585-B6D7-4DFB-AE4B-4499C00B6211
- ObjectType: RQM_SAFETY_MANUAL_ITEM

### da5baaeda96508962fa00ad04d171292a58453aa2b53251c0611a1d64a430e4e: Safety requirements required from other components
- ChapterNumber: 10.4
- ObjectType: DocItem

#### 951fe101ca33629568cc0282d0bfb2b3406c978b65b4771bd759019910e315f2
This component does not require safety requirements from other components.
- ObjectType: DocItem

### 550c8bc58c4f765fd2dedc3d4df24d5d1eafd1653f2c9d2aa9214cca2517ee01: Dependencies to hardware
- ChapterNumber: 10.5
- ObjectType: DocItem

#### ee1ae68a6c999a35a205c9c8465f073991f61775c9fb54b156323a8ad423db9a
This component requires exclusive access to the hardware registers of the unit it is intended to control. See the technical reference for the hardware register names and used hardware manuals.
- ForeignTraceId: SMI-116969
- ForeignAlternativeId: SMI-0C29D863-8480-44A8-B4D2-FB4647216B8B
- ObjectType: RQM_SAFETY_MANUAL_ITEM

#### 21956aeb42348b9c4b5729eb6a049982afdbb38643310440f625e3458df5ff5f: S32K14x
- ChapterNumber: 10.5.1
- ObjectType: DocItem

##### 9a14d925b75d32b94cb6f62c6eef6ca19618f5babb89bc9639b55474192bebc3
The following hardware safety manual has been taken into consideration:
File Name: S32K14XSM.pdf
S32K14x Series Safety Manual
Doc. No. S32K14XSM
This OS does not implement any requirement from that safety manuals.
It is assumed that the requirements related to OS functionality are related to latent faults only and the aimed ASIL is still achievable without implementation by the OS.
- ForeignTraceId: SMI-116970
- ForeignAlternativeId: SMI-8C043EEA-7DD3-439F-9D71-1A7EF0481788
- ObjectType: RQM_SAFETY_MANUAL_ITEM

#### 80241416decaee9a3f2ebdb2cd30c0524566eb56c9cf91e8a1fe3c63f4af7933: DRA7x
- ChapterNumber: 10.5.2
- ObjectType: DocItem

##### fde13a0a603db08edc1d4aa5ff8a39581d0e416a2cabb104d5cecbec00ea4624
The following hardware safety manual has been taken into consideration:
File Name: SPRUII9.pdf
Safety Manual for TDA2x, TDA2Px, and DRA7x Applications Processors
Literature. No. SPRUII9
This OS does not implement any requirement from the safety manuals.
It is assumed that the requirements related to OS functionality are related to latent faults only and the aimed ASIL is still achievable without implementation by the OS.
- ForeignTraceId: SMI-147939
- ForeignAlternativeId: SMI-3D3F0F84-C36A-4C5D-8C6D-7A318C846092
- ObjectType: RQM_SAFETY_MANUAL_ITEM

#### 7dcf2d22ffe0da21e3eb8e1205b50a5b70367881158bbd424b14041a29875935: STA1385
- ChapterNumber: 10.5.3
- ForeignTraceId: OBJ948593
- ForeignAlternativeId: OBJ-754C1065-3102-475F-889F-B7ECB4A6E862
- ObjectType: TRACE_ITEM

##### 4fe355c3b4583262fd90fe0f3856510b62da486d108784abd92e365a54514d3b
The following hardware safety manual has been taken into consideration:
File Name: ST_Telemaco3P_STA1385_SM.pdf
Funtional Safety Manual for Telemaco3P(STA1385) Rev1.3
Literature. No. ST_Telemaco3P_STA1385_SM
This OS does not implement any requirement from the safety manuals.
It is assumed that the requirements related to OS functionality are related to latent faults only and the aimed ASIL is still achievable without implementation by the OS.
- ForeignTraceId: SMI-431926
- ForeignAlternativeId: SMI-46AA7467-98A2-4F51-8ACF-ADE1272A6D4B
- ObjectType: RQM_SAFETY_MANUAL_ITEM

#### 883100488f13e636a178c3243ece42912f38aa565cb6e8deb30c26aa68fe1252: IMX8x
- ChapterNumber: 10.5.4
- ForeignTraceId: OBJ948594
- ForeignAlternativeId: OBJ-EE4F83C0-7115-4775-BBB9-A41353264A61
- ObjectType: TRACE_ITEM

##### 1bd15c1d1ce5c11105d24e3dba46b282fdfa931da90a94cadea84d94c0bb8d32
The following hardware safety manual has been taken into consideration:
File Name: iMX8M8XSM.pdf
Funtional i.MX 8/8X Applications Processor Safety
Manual. Document Number: iMX8M8XSM Rev. 0, 1 April 2019
This OS does not implement any requirement from the safety manuals.
It is assumed that the requirements related to OS functionality are related to latent faults only and the aimed ASIL is still achievable without implementation by the OS.
- ForeignTraceId: SMI-431927
- ForeignAlternativeId: SMI-613617C6-9F92-4F6F-9623-13552E3FFD81
- ObjectType: RQM_SAFETY_MANUAL_ITEM

#### 77521d6eea978db9a66a65c5e278e3729754009f0cc991c50d1cd7ce8f18a232: S32G274A
- ChapterNumber: 10.5.5
- ObjectType: DocItem

##### f623af62ce0851e5856e9c1a83d9f102558c9ba59c7bcea851c6e9b5c3c35a3a
The following hardware safety manual has been taken into consideration:
File Name: S32G274ASM.pdf, including Assumptions.xlsx, Safety_Mechanisms.xlsx and Module_Classification.xlsx
Funtional S32G274A Safety Manual
Document identifier: S32G274ASM, Rev. 1 Draft C,30 Aug 2019
This OS does not implement any requirement from the safety manuals.
It is assumed that the requirements related to OS functionality are related to latent faults only and the aimed ASIL is still achievable without implementation by the OS.
- ForeignTraceId: SMI-431713
- ForeignAlternativeId: SMI-081B2BC7-A108-498F-9B5C-BA7D923CF5FA
- ObjectType: RQM_SAFETY_MANUAL_ITEM

#### bfb06f1bfa8354ae0c9f71c5b0df91b8878427ab9508a20003fddede34e87fd6: CYT2Bx
- ChapterNumber: 10.5.6
- ObjectType: DocItem

##### a01855816bb3a41bd3c3a4232e0d35635ded3a59e0dccac48170057c3bc79435
The following hardware safety manual has been taken into consideration:
File Name: SM-002-20312_0E_V.pdf
Traveo™ II Automotive Body Controller Entry Safety Manual Doc. No. 002-20312 Rev. *E
This OS implements safety requirement MXS40-319. Any other requirement from the safety manual is not implemented by this OS.
It is assumed that the requirements related to OS functionality are related to latent faults only and the aimed ASIL is still achievable without implementation by the OS.
- ForeignTraceId: SMI-568209
- ForeignAlternativeId: SMI-8E5D2FDB-C416-4611-B35C-ED0D83BF395E
- ObjectType: RQM_SAFETY_MANUAL_ITEM

#### 032eed5adeb816ae941ffdc3d43474764c2fff40075cfd794fb2ce9a65787346: CYT3Dx/CYT4Dx
- ChapterNumber: 10.5.7
- ObjectType: DocItem

##### d2b07a7fd6d2ab213950480a1dcf5f5915b4b44b9c4dbff87ef47ee924149d33
The following hardware safety manual has been taken into consideration:
File Name: CYT3D_4D_SafetyManual_2021_03_002-31415_0A.pdf
Traveo II Automotive Cluster 2D Safety Manual
Document Number: 002-31415 Rev. *A
This OS implements safety requirement MXS40-319. Any other requirement from the safety manual is not implemented by this OS.
It is assumed that the requirements related to OS functionality are related to latent faults only and the aimed ASIL is still achievable without implementation by the OS.
- ForeignTraceId: SMI-672568
- ForeignAlternativeId: SMI-95A21483-FFF0-4C5B-8762-168A3E011A96
- ObjectType: RQM_SAFETY_MANUAL_ITEM

#### 1e1ccfe94fb4d98e35902cd7df0e966122787d845378c9b410e1932403bdabcf: TDA3x
- ChapterNumber: 10.5.8
- ObjectType: DocItem

##### 4679e5c71dfc7d67a55705a1a5da3000927f809e981f50305f398a3b10c65a28
The following hardware safety manual has been taken into consideration:
File Name: TDA3x_SafetyManual_SPRUIG2_September2017.pdf, including TDA3_PPAP_FMEDA_customerVersion(6).xlsm
Safety Manual for TDA3x Automotive Vision safety-critical Applications Processors
Document identifier: SPRUIG2 , September 2017
This OS does not implement any requirement from the safety manuals.
It is assumed that the requirements related to OS functionality are related to latent faults only and the aimed ASIL is still achievable without implementation by the OS.
- ForeignTraceId: SMI-793100
- ForeignAlternativeId: SMI-E00F7287-E8E9-4D94-8B69-7162F939E053
- ObjectType: RQM_SAFETY_MANUAL_ITEM

#### 79725955a429e398699077c2cc90765f6c7d70cfa1d6c024f6ad36ef79f92af3: S32K3XX
- ChapterNumber: 10.5.9
- ObjectType: DocItem

##### a7b1f5ff6751e883cd7a9cdf6dca613999b9ed3aea21ed675a2622bc447e4021
The following hardware safety manual has been taken into consideration:
File Name: S32K3XXSM.pdf, including Addendum_S32K3xx.xlsx
Funtional S32K3XX Safety Manual
Document identifier: S32K3XXSM, Rev. 1, Sep 2021
File Name: S32K396 Preliminary Safety Manual.pdf, including Addendum_S32K396.xlsx
Funtional S32K396 Safety Manual
Document identifier: S32K396SM, Rev. 1, Nov 2021
This OS does not implement any requirement from the safety manuals.
It is assumed that the requirements related to OS functionality are related to latent faults only and the aimed ASIL is still achievable without implementation by the OS.
- ForeignTraceId: SMI-844633
- ForeignAlternativeId: SMI-3EEEB113-AEC4-49E3-9F06-A495FCCFA7C6
- ObjectType: RQM_SAFETY_MANUAL_ITEM

#### f0f883f48026f21226babec4610d4df7d2d6fa8463784c6a7376984146119d9c: S32R45
- ChapterNumber: 10.5.10
- ObjectType: DocItem

##### b2a25986d519d66ad59ad4e6f4104b191bf8d471ece57fc13790b8ecaa31a8ed
The following hardware safety manual has been taken into consideration:
File Name: S32R45SM.pdf, including Addendum_S32R45.xlsx
Funtional S32R45 Safety Manual
Document identifier: S32R45SM, Rev. 1, Aug 2021
This OS does not implement any requirement from the safety manuals.
It is assumed that the requirements related to OS functionality are related to latent faults only and the aimed ASIL is still achievable without implementation by the OS.
- ForeignTraceId: SMI-844634
- ForeignAlternativeId: SMI-022E2E14-DC88-43C0-B60B-B0F0C7A06576
- ObjectType: RQM_SAFETY_MANUAL_ITEM

#### e5a4fcfc91ffe139ed53c33148740484c37a2a5b75a2ba37773c5d9daf56d69b: CYT3Bx/CYT4Bx
- ChapterNumber: 10.5.11
- ForeignTraceId: SMI-850672
- ForeignAlternativeId: SMI-8B39AC7B-1BF4-41DE-81A0-554F901177A7
- ObjectType: RQM_SAFETY_MANUAL_ITEM

##### f273ae1cf94c090f59fdc2211c744ea35989939781e95b696fc3bde846fd9189
The following hardware safety manual has been taken into consideration:
File Name: CYT4BB-BF_3BB_BH_SM_2021-08-25_002-25937_0E_V.pdf
TRAVEO™ II Automotive Body Controller High Safety Manual
Document Number: 002-25937 Rev. *E
MICROSAR OS implements safety requirement MXS40-319. Any other requirement from the safety manual is not implemented by this OS.
It is assumed that the requirements related to OS functionality are related to latent faults only and the aimed ASIL is still achievable without implementation by the OS.
- ObjectType: DocItem

#### b51388c280f404ad953b1e009e20dd300d387b071d166675f46e100360dfe330: BCM89107
- ChapterNumber: 10.5.12
- ForeignTraceId: SMI-853203
- ForeignAlternativeId: SMI-DA034227-DA3A-44F8-B923-30EBB0216B9E
- ObjectType: RQM_SAFETY_MANUAL_ITEM

##### cdb87e37e47ee78bcf325169a87d8d615f97926fda5875dd2bbf01fa0117639f
The following hardware safety manual has been taken into consideration:
File Name: BCM89107_SM_89107-RM200l.pdf
BCM89107 Safety Manual, Preliminary Reference Manual
Document identifier: 89107-RM200 February 1, 2018
This OS does not implement any requirement from the safety manuals.
It is assumed that the requirements related to OS functionality are related to latent faults only and the aimed ASIL is still achievable without implementation by the OS.
- ObjectType: DocItem

#### fdd617fd2453ffa92f437c9d1fc12be6b7e182f96145d45227f3d466c1e1fa1f: CYT2Cx
- ChapterNumber: 10.5.13
- ForeignTraceId: SMI-886602
- ForeignAlternativeId: SMI-4A033EEF-8C81-459E-8EDB-EC7062974AF8
- ObjectType: RQM_SAFETY_MANUAL_ITEM

##### c145922055e1bc0c6b10d25ac767da14a901c8fec04e952bb2ce98f5b6d67c99
The following hardware safety manual has been taken into consideration:
File Name: CYT2_B6_B7_B9_BL_CL_SM__002-20312_0G_V.pdf
Traveo™ T2G Automotive Body/Cluster Controller Entry Safety Manual
Document No. 002-20312 Rev. *G, 2022-02-21
This OS implements safety requirement MXS40-319. Any other requirement from the safety manual is not implemented by this OS.
It is assumed that the requirements related to OS functionality are related to latent faults only and the aimed ASIL is still achievable without implementation by the OS.
- ObjectType: DocItem

## 787053c9c4fc581078dd85da8f113f64110a1ce2679ba5b6017c3334ec013e9d: Safety Manual Rte
- ChapterNumber: 11
- ObjectType: DocItem

### c9831cf3dbe7435644d1587403001887d80472458944f449823a07a47543621f: Assumed safety requirements
- ChapterNumber: 11.1
- ObjectType: DocItem

#### 05e3ed675ae7e6326e12516ef0495b310d14ea07bd6024c54d43568735e653c8
This component assumes the following safety requirements:
| ID | Safety Requirement | Associated TSR | ASIL |
| --- | --- | --- | --- |
| CREQ-1024 | Rte shall provide a service to initiate the transmission of data elements with last-is-best semantic for explicit S/R communication. | TSR-16,TSR-12,TSR-111108,TSR-10 | ASIL D |
| CREQ-1021 | Rte shall provide a service to copy the received data element to a buffer with last-is-best semantic for explicit S/R communication. | TSR-16,TSR-111108,TSR-10,TSR-12 | ASIL D |
| CREQ-1022 | Rte shall provide a service to get the value of the received data element with last-is-best semantic for explicit S/R communication. | TSR-16,TSR-12 | ASIL D |
| CREQ-1031 | Rte shall provide a service to read a data element for implicit S/R communication. | TSR-12,TSR-16 | ASIL D |
| CREQ-1029 | Rte shall provide a service to write a data element for implicit S/R communication. | TSR-16,TSR-12 | ASIL D |
| CREQ-1041 | Rte shall provide a service to get the reference of a data element to be written for implicit S/R communication. | TSR-16,TSR-12 | ASIL D |
| CREQ-1037 | Rte shall provide a service to get the status of a data element for implicit S/R communication. | TSR-16,TSR-12 | ASIL D |
| CREQ-1033 | Rte shall provide a service to access the update flag for a data element for explicit S/R communication. | TSR-12,TSR-16 | ASIL D |
| CREQ-1036 | Rte shall provide a "Never-received" status of a data element for S/R communication. | TSR-16,TSR-12 | ASIL D |
| CREQ-1023 | Rte shall provide a service to initiate the transmission of a data element with queued semantic for explicit S/R communication. | TSR-111108,TSR-12,TSR-10,TSR-16 | ASIL D |
| CREQ-1025 | Rte shall provide a service to initiate the reception of a data element with queued semantic for explicit S/R communication. | TSR-111108,TSR-12,TSR-16,TSR-10 | ASIL D |
| CREQ-1042 | Rte shall provide a service to initiate a client-server communication. | TSR-16,TSR-12 | ASIL D |
| CREQ-1043 | Rte shall provide a service to get the result of an asynchronous client-server call. | TSR-12,TSR-16 | ASIL D |
| CREQ-1151 | Rte shall provide the optional usage of one or several data transformers. | TSR-10,TSR-104422 | ASIL D |
| CREQ-1109 | Rte shall provide mode management. | TSR-100551 | ASIL D |
| CREQ-1055 | Rte shall provide a service to get the currently active mode. | TSR-100551 | ASIL D |
| CREQ-1052 | Rte shall provide a service to get the currently active, previous and next mode. | TSR-100551 | ASIL D |
| CREQ-1053 | Rte shall provide a service to initiate a mode switch. | TSR-100551 | ASIL D |
| CREQ-1299 | Rte shall provide Nv data communication. | TSR-5,TSR-4 | ASIL D |
| CREQ-1150 | Rte shall provide a callback to copy data from a NVM buffer to RTE. | TSR-5 | ASIL D |
| CREQ-1148 | Rte shall provide a callback to copy data from RTE to a NVM buffer. | TSR-4 | ASIL D |
| CREQ-1144 | Rte shall provide a callback to get notified about a finished NVM job. | TSR-4,TSR-5 | ASIL D |
| CREQ-1147 | Rte shall provide a callback to get notified about a requested mirror initialization. | TSR-5,TSR-4 | ASIL D |
| CREQ-1046 | Rte shall provide a service to read Inter-Runnable Variables with explicit behavior. | TSR-16 | ASIL D |
| CREQ-1048 | Rte shall provide a service to write Inter-Runnable Variables with explicit behavior. | TSR-16 | ASIL D |
| CREQ-1047 | Rte shall provide a service to read Inter-Runnable Variables with implicit behavior. | TSR-16 | ASIL D |
| CREQ-1044 | Rte shall provide a service to write Inter-Runnable Variables with implicit behavior. | TSR-16 | ASIL D |
| CREQ-149683 | Rte shall provide a service to get the reference of an Inter-Runnable Variable with implicit behavior for write purposes. | TSR-16 | ASIL D |
| CREQ-174803 | Rte shall provide a service to initiate the triggering of runnable entities over internal trigger communication. | TSR-6 | ASIL D |
| CREQ-1045 | Rte shall provide a service to access per-instance memory. | TSR-16 | ASIL D |
| CREQ-1051 | Rte shall provide a service to enter an exclusive area. | TSR-101876 | ASIL D |
| CREQ-1050 | Rte shall provide a service to leave an exclusive area. | TSR-101876 | ASIL D |
| CREQ-1056 | Rte's Basic Software Scheduler shall provide a service to enter an exclusive area of a BSW Module. | TSR-101876 | ASIL D |
| CREQ-1049 | Rte's Basic Software Scheduler shall provide a service to leave an exclusive area of a BSW Module. | TSR-101876 | ASIL D |
| CREQ-1068 | Rte shall provide a service to access internal calibration parameters. | TSR-5 | ASIL D |
| CREQ-1075 | Rte shall provide a service to access calibration parameters accessible via ports. | TSR-5 | ASIL D |
| CREQ-1059 | Rte shall provide a service to initialize itself. | TSR-1 | ASIL D |
| CREQ-184330 | Rte shall provide a service to activate the triggers for cyclic and background runnables. | TSR-1 | ASIL D |
| CREQ-1073 | Rte's Basic Software Scheduler shall provide a service to initialize itself. | TSR-1 | ASIL D |
| CREQ-1161 | Rte shall provide a service to trigger executable entities. | TSR-6 | ASIL D |
| CREQ-1165 | Rte shall use schedule points to invoke the scheduler of the OS. | TSR-6 | ASIL D |
| CREQ-1129 | Rte shall provide the event handling of TimingEvents to trigger a runnable. | TSR-6 | ASIL D |
| CREQ-1112 | Rte shall provide the event handling of SwcModeSwitchEvents to trigger a runnable. | TSR-6 | ASIL D |
| CREQ-1124 | Rte shall provide the event handling of AsynchronousServerCallReturnsEvents to trigger a runnable. | TSR-6 | ASIL D |
| CREQ-1126 | Rte shall provide the event handling of OperationInvokedEvents to trigger a runnable. | TSR-6 | ASIL D |
| CREQ-1118 | Rte shall provide the event handling of DataReceivedEvents to trigger a runnable. | TSR-6 | ASIL D |
| CREQ-1132 | Rte shall provide the event handling of ModeSwitchedAckEvents to trigger a runnable. | TSR-6 | ASIL D |
| CREQ-1114 | Rte shall provide the event handling of the InitEvents to trigger a runnable. | TSR-6 | ASIL D |
| CREQ-174850 | Rte shall provide the event handling of InternalTriggerOccuredEvents to trigger a runnable. | TSR-6 | ASIL D |
| CREQ-1295 | Rte shall provide the event handling of TimingEvents to trigger a schedulable entity. | TSR-6 | ASIL D |
| CREQ-1152 | Rte shall provide a "RTE_AND_SCHM_UNINIT" state. | TSR-6 | ASIL D |
| CREQ-1164 | Rte shall provide a "RTE_UNINT_SCHM_INIT" state. | TSR-6 | ASIL D |
| CREQ-1166 | Rte shall provide a "INIT" state. | TSR-6 | ASIL D |
This component in addition to the assumed safety requirements ensures freedom from interference with respect to memory (and timing) with up to ASIL D.
- ForeignTraceId: SMI-323
- ForeignAlternativeId: SMI-D75B4A45-F68E-4306-8162-E0147DFE02AB
- ObjectType: RQM_SAFETY_MANUAL_ITEM

### 91edf9d712b2a9945061b3d15b9eef15a238112fdb5205b05181c6358bc91229: Configuration constraints
- ChapterNumber: 11.2
- ObjectType: DocItem

#### 73f1e527ae885cda70054a87c156705aef11389d90d573853ae940d98368b136
The user of MICROSAR Safe shall disable online calibration and measurement during series production.
The RTE can be generated with online calibration and measurement enabled for series production, but they shall be made inoperable for normal operation. Vector's XCP can e.g. be disabled safely during runtime by ASIL software.
- ForeignTraceId: SMI-2066
- ForeignAlternativeId: SMI-4FD826C7-23FC-4DDF-925A-AC83DF8A76E0
- ObjectType: RQM_SAFETY_MANUAL_ITEM

#### a38677ea3061da0a7a5f838edc5a568cda4807ab1fde47046f47328400e13bb7
The user of MICROSAR Safe shall not use RTE Implementation Plugins for ASIL software.
RTE implementation plugins can be used to partially replace RTE APIs with custom implementations.
The user of MICROSAR Safe shall ensure that the safety related parts of the RTE do not use RTE implementation plugins.
The RTE Analyzer lists used RTE implementation plugins to assist in this integration step.
- ForeignTraceId: SMI-530545
- ForeignAlternativeId: SMI-402E3EC3-9B0A-4C59-95A0-2AE52D78591B
- ObjectType: RQM_SAFETY_MANUAL_ITEM

#### cf65aa32398e265adf80fd8274c9ded71d8ce9681cef83b9d753e100322862b5
The user of MICROSAR Safe shall disable Logical Execution Time Support for ASIL software
No Rte_LetFrame_<frame>_Release and Rte_LetFrame_<frame>_Terminate functions shall exist in the code.
The RTE Analyzer reports not supported template variants in case it detects usage of LET.
- ForeignTraceId: SMI-764244
- ForeignAlternativeId: SMI-2014B717-8002-41B1-BC88-8E6D01B572C0
- ObjectType: RQM_SAFETY_MANUAL_ITEM

#### a9106f611a168427607d76ae5e51b3947a294469917f422e9ede6b8cc79a38df
The user of MICROSAR Safe shall disable ArrayImplPolicy PayloadAsPointerToArray for safety related SWCs
The RTE Analyzer reports not supported template variants in case it detects usage of arrays with ArrayImplPolicy set to PayloadAsPointerToArray.
- ForeignTraceId: SMI-1102567
- ForeignAlternativeId: SMI-4FD433A2-9281-4DB9-B3E0-2D7570174D8E
- ObjectType: RQM_SAFETY_MANUAL_ITEM

### 6770ffaffbe02f84d830bb30b6e5836747907078486637c7461cc847cdb2f7d4: Additional verification measures
- ChapterNumber: 11.3
- ObjectType: DocItem

#### 8deff13545a1622ba3728a2883b58e791807a0c229cfea24e26e28cd2232ca1f
Please note that the RTE Generator and RTE Analyzer only implement measures to detect systematic faults by the software. No measures are implemented to detect or mitigate random faults on the computer used for generation.
- ObjectType: DocItem

#### c75d5bdb2e84bc89355ac2bfdfbcfc658da600ec352fd2bfefa482a02993d628
The user of MICROSAR Safe shall execute the RTE Analyzer.
The RTE Analyzer performs checks to identify faults in the generated RTE. Especially out-of-bounds accesses within the RTE are detected. If the RTE Analyzer reports a fault, the generated RTE cannot be used. Moreover it provides the user of MICROSAR Safe with feedback what was generated. This feedback shall be reviewed during integration testing against the intended software design and its configuration.
For details on how to execute the RTE Analyzer, please refer to the Technical Reference of the RTE Analyzer.
- ForeignTraceId: SMI-322
- ForeignAlternativeId: SMI-BC94FD54-28AC-4262-A2ED-9D929DD394AA
- ObjectType: RQM_SAFETY_MANUAL_ITEM

#### bedcf7cc85603b50972153f3d1f2d8402c67357a5a2d30bc319801c05c5ea1a3
The user of MICROSAR Safe shall execute the RTE Analyzer on Windows.
MICROSAR Classic RTE Analyzer for Linux is not yet qualified for series production.
- ForeignTraceId: SMI-860026
- ForeignAlternativeId: SMI-4C05A454-6AE2-48B5-90AC-4DF03C04F550
- ObjectType: RQM_SAFETY_MANUAL_ITEM

#### 902ce65b4b323e608cb9c5e4f9b875a59ab68c7396b1a8f03ce1bdfb3f7022c1
The user of MICROSAR Safe shall execute the RTE Analyzer with extended configuration feedback commandline switch for fail-operational systems.
The RTE Analyzer performs checks to identify faults in the generated RTE. By default, the RTE Analyzer configuration feedback is only printed for ASIL partitions. An MPU can protect the ASIL partition from memory corruption that is caused by the QM partition. However, the QM partition can also have an impact on the scheduling of the ASIL partition that needs to be considered for fail-operational systems.
This is especially relevant when there are connections between ASIL and QM SWCs.
When RTE Analyzer is started with the commandline switch for the extended configuration feedback, the configuration feedback is also printed for QM partitions.
For details on how to execute the RTE Analyzer, please refer to the Technical Reference of the RTE Analyzer.
- ForeignTraceId: SMI-466082
- ForeignAlternativeId: SMI-868822C9-B9D9-43F5-AF81-2EF92EC51BAA
- ObjectType: RQM_SAFETY_MANUAL_ITEM

#### fbbdb02d6b60faedb892f449d844ffbbab7af7b56340e5365b96a4b63ec018bc
The user of MICROSAR Safe shall ensure that the RTE Analyzer does not report unsupported templates.
The generated RTE code is based on templates. The templates are instantiated by the RTE Generator in different variants. The RTE Analyzer verifies that the analyzed template variants have been tested during the development of the RTE Generator according to ISO 26262.
The last section of the RTE Analyzer configuration feedback report provides information about the template variants.
The report must show that no unsupported templates have been found.
- ForeignTraceId: SMI-36067
- ForeignAlternativeId: SMI-7A262275-8DD3-48E3-905B-C9ACC722533B
- ObjectType: RQM_SAFETY_MANUAL_ITEM

#### 0ec6a25a3bd81a440dfcdc014ae8a07b3e7f44537b13b0e56a0f3918110d93a8
The user of MICROSAR Safe shall ensure that the variables Rte_InitState<Core> are mapped to memory sections with the highest ASIL level.
The RTE uses RTE_START_SEC_VAR_<Partition>_ZERO_INIT_8BIT to map the Rte_InitState variables.
In fail-safe systems with the Partitioning approach where BSW (Com, LdCom, NvM) is QM, the initialization of the Rte can be done from the partition that contains EcuM (QM Partition after StartOS).
Also Rte_InitState can be mapped to this QM partition as long as the execution of the safety-related entities is supervised by additional safety mechanisms (e.g. a watchdog).
When Rte_InitState is mapped to an ASIL partition, QM ECUM needs to call the lifecycle APIs within trusted functions.
This requirement is necessary to ensure freedom from interference with respect to memory by this component.
- ForeignTraceId: SMI-763706
- ForeignAlternativeId: SMI-33E1300A-E5B1-4F07-BD9E-EBF8B85D2DF2
- ObjectType: RQM_SAFETY_MANUAL_ITEM

#### 9aaa37097754fb19c945cdc4e2ab29538925f65792f421d10ff8cfbc00727a2e: Guided integration testing
- ChapterNumber: 11.3.1
- ObjectType: DocItem

##### ff5c5f19ff1f84125c766aec94c6a76fc5430e7e819518f810a8d2bbc31341d8
Residual faults in the RTE Generator can only be found during integration testing. Vector assumes that the user of MICROSAR Safe performs an integration testing and verification of software safety requirements according to ISO 26262 Part 6 Clauses 10 and 11 (see also SMI-4). To support this integration testing, the RTE Analyzer produces a configuration feedback report.
Please refer to the Technical Reference of the RTE Analyzer for a description of the configuration feedback report.
The following subsections describe the requirements that must be fulfilled during integration testing and verification of software safety requirements.
Each Safety Manual Item (SMI) is structured in the following way:
- The requirement that must be fulfilled
- Explanation of the requirement and a rationale
- Recommended configuration constraints (optional)
- Recommended means of complying with the requirement (optional)
- Details on the information provided by the RTE Analyzer supporting this requirement
- ObjectType: DocItem

##### 33648532e4431dc2c7d3fe0fd5da50ae52b99aa4aed4286ad699aca361f012bd: BSW configuration
- ChapterNumber: 11.3.1.1
- ObjectType: DocItem

###### 78c5f5880ceaafb549ff2c2e8e61ff51ebd2c26a5273ccc8c2e5b7572c935faf
The user of MICROSAR Safe shall ensure that the RTE and the operating system assume the same scheduling properties.
The scheduling properties of the RTE tasks depend on the configuration of the operating system. The scheduling properties are e.g. preemptability, core assignment or task priority.
The RTE Analyzer lists the scheduling properties in the configuration feedback report to assist in this integration step. The scheduling properties listed in the feedback report shall be verified.
- ForeignTraceId: SMI-2124
- ForeignAlternativeId: SMI-03844F69-F1C5-40DA-B467-2466B202ED99
- ObjectType: RQM_SAFETY_MANUAL_ITEM

###### b89cc146177e79246dcc937ebe226f01c1d8193444f6b0194a9b9b5ea5dbec76
The user of MICROSAR Safe shall ensure that the assumptions of the operating system and the RTE are the same with regards to the locking behavior of the spinlocks.
The RTE generator uses spinlocks from the operating system to protect inter-core communication. Spinlocks must not be called concurrently on the same core. The operating system optionally provides spinlocks that can prevent these concurrent accesses on the same core. If this protection by the operating system is not used, the RTE generator has to prevent concurrent calls to the spinlock APIs on the same core.
Verification can e.g. be performed by review of the configuration feedback report.
The RTE Analyzer lists spinlocks that are not protected by the RTE to assist in this integration step.
- ForeignTraceId: SMI-2129
- ForeignAlternativeId: SMI-26C0219C-B74E-43AF-821E-452FA33C670A
- ObjectType: RQM_SAFETY_MANUAL_ITEM

###### 90c906b0a543dc647ba49d9dc739e84ef2806ca2d6e56f77a9c1aef0bb2aa9ca
The user of MICROSAR Safe shall ensure that the configuration of the COM and the RTE are consistent.
The interfaces to the COM that are used for signal reception use void pointers as parameter. Inconsistencies between the configuration of the COM and the RTE might lead to memory corruption by the COM. During integration, the size assumptions between the COM and the RTE shall be compared.
Verification can be performed by review of the generated configuration and/or static code analysis.
The RTE Analyzer lists relevant calls to assist in this integration step.
The RTE Analyzer listing includes the number of written bytes for the MICROSAR COM.
The RTE Analyzer lists the signals that are assigned to the individual partitions with callbacks.
The RTE Analyzer lists the signals that are assigned to the individual partitions without callbacks.
- ForeignTraceId: SMI-684
- ForeignAlternativeId: SMI-A00A2349-1814-4B59-91C8-5D6AE013067B
- ObjectType: RQM_SAFETY_MANUAL_ITEM

###### 45b8a295c236dbda4cb26d7142fb1df0c40760cba004da4d8266bd39c7f0f808
The user of MICROSAR Safe shall ensure that the configuration of the NVM and the RTE are consistent.
The interfaces to the NVM that are used to handle NV Block SWCs use void pointers as parameters.
Inconsistencies between the configuration of the NVM and the RTE might lead to memory corruption by the RTE.
During integration, the size assumptions between the NVM and the RTE shall be compared and it shall be checked that the intended block is accessed and has the expected layout.
Moreover it has to be assured that the NVM calls the Rte_GetMirror and Rte_SetMirror callbacks to store and restore the NVM data at the point in time that is expected by the application.
The Rte_GetMirror and Rte_SetMirror functions, the block size and whether the block is read or written during read and write all can typically be found in the generated data structures of NVM in NvM_Cfg.c.
The value that is used in the checks in the Rte_GetMirror and Rte_SetMirror callbacks needs to be the same as the block size.
if (size <= <BlockSize>U)
Verification can e.g. be performed by review of the generated configuration, static code analysis and/or integration testing.
The RTE Analyzer lists relevant calls to assist in this integration step.
For MICROSAR Classic NVM, the RTE Analyzer also checks that the written data does not exceed the maximum internal NVM buffer length.
The RTE Analyzer lists the detected partition that contains NVM.
- ForeignTraceId: SMI-685
- ForeignAlternativeId: SMI-8C1A4AEF-09D6-431D-8672-DC8A92BD6A35
- ObjectType: RQM_SAFETY_MANUAL_ITEM

##### 4dd995c5d5d74098a3217e53cc48bc582004385df1a844a6581736e96c37f402: Executable Entity Scheduling
- ChapterNumber: 11.3.1.2
- ObjectType: DocItem

###### f35a8758c760a2dfe246e7d3e536e7c0eb8fc54d7fb319599cb6f08484a870b3
The user of MICROSAR Safe shall ensure that all safety-related executable entities are triggered with their correct conditions.
These conditions are:
- cylic triggers with cycle time and offset
- init triggers
- background triggers
- triggers fired by RTE APIs
Safety related executable entities include server runnables that are called with direct function calls from the ASIL partition.
If triggers have a dependency on modes, the scheduling has to be verified for all modes. Modes can be switched with the Rte_Switch API.
Moreover, mode switching can also happen in the task that contains the mode switch triggers or mode disablings. When mode receivers are distributed on several cores, the RTE synchronizes the mode machines in these tasks. Thus mode triggered runnables on other cores can block the scheduling on the core that initiated the mode switch. Please note that, if these tasks are tasks with lower safety level and freedom from interference with regards to memory is not ensured, also other code in the same partition can corrupt the mode disablings and lead to unintended blocking of the tasks.
Moreover queues and APIs with waitpoints can lead to blocking of ASIL tasks. See SMI-2125 and SMI-2064.
This needs to be considered when designing fail-operational systems.
All partitions need to be analyzed for fail-operational systems, not only the ASIL partitions.
Triggers can be decoupled by the minimum start interval functionality and the data reception filter functionality.
The scheduling of the executable entities also depends on the configuration of the operating system, the used controller, other running tasks and interrupt service routines and the resource usage of the entities that are implemented by the user.
Vector requires not using the minimum start interval for safety-related runnables.
Vector requires not using the data reception filter functionality for safety-related runnables.
Vector requires not using activation reasons for safety-related runnables.
Vector recommends not using background triggers for safety-related functionality.
Vector recommends not distributing mode receivers on different cores.
Vector requires not using QM mode receivers on different cores for fail-operational systems.
Vector recommends using cyclic scheduling without mode dependencies and using of a watchdog as safety mechanism for safety-related entities where possible.
Cyclic triggers are e.g. scheduled deterministically. Thus, an integration test verifying that safety-related functionality is scheduled at the expected times may be sufficient.
The RTE Analyzer lists the executable entities of SWCs and the tasks in which they are executed to assist in this integration step.
The RTE Analyzer lists recursive calls to assist in this integration step.
- ForeignTraceId: SMI-2063
- ForeignAlternativeId: SMI-F49E7EC2-88E3-4C8A-811C-C12463B0F0E8
- ObjectType: RQM_SAFETY_MANUAL_ITEM

###### 5f53d2c414acdead3120281facde7152066a6e5b6d2977256282e1c0ac1a36ee
The user of MICROSAR Safe shall ensure that reentrant runnables are reentrant.
Runnables can be called reentrantly from multiple tasks. Their implementation needs to support this use case.
Verification can e.g. be performed by review, static code analysis and/or integration testing.
The RTE Analyzer lists all runnables of SWCs that are called from concurrent tasks to assist in this integration step.
Implicit exclusive areas and nonpreemptive tasks can be configured to prevent concurrent execution.
- ForeignTraceId: SMI-2128
- ForeignAlternativeId: SMI-54D0EB5B-2EEC-4416-936D-898DBF57DA29
- ObjectType: RQM_SAFETY_MANUAL_ITEM

###### a50ddff0912fa71c22524f0f262c8b5fc54ad46753921982c39661d7ec3a5fc1
The user of MICROSAR Safe shall ensure that the timeouts configured for blocking and non-blocking APIs that are used in safety-related executable entities are adequately addressed.
If a timeout for an API is used as a safety mechanism (E.g. no checkpoint with deadline monitoring in the task), the user of MICROSAR Safe shall also ensure that the timeout value is adequate.
Relevant timeouts are:
- timeouts of Rte_Call APIs
- timeouts of Rte_Result APIs
- timeouts of Rte_Receive APIs
- timeouts of Rte_Feedback APIs
- timeouts of Rte_SwitchAck APIs
The timeouts also depend on the configuration of the operating system, the used controller, other running tasks and interrupt service routines and the resource usage of entities that are implemented by the user.
For blocking APIs:
Vector recommends not using blocking APIs in safety-related entities except for cross partition client-/server communication.
Vector strongly recommends not using blocking APIs without timeout.
Vector requires not using blocking APIs without timeout for fail-operational systems.
This is necessary because otherwise the APIs will wait forever after a communication loss and cannot be used for additional requests until the RTE is restarted.
For non-blocking APIs:
Vector requires not using non-blocking APIs with timeout in safety-related entities.
A review may be sufficient to verify that timeout handling is implemented properly by the SWC.
If no other safety mechanism is in place, a test that the timeout is notified at the expected time by the RTE can be used as means of verification.
The RTE Analyzer lists the blocking and non-blocking APIs of SWCs with and without timeout to assist in this integration step.
- ForeignTraceId: SMI-2064
- ForeignAlternativeId: SMI-C5F76ACD-E6A5-43DC-8657-417077F9EB05
- ObjectType: RQM_SAFETY_MANUAL_ITEM

###### ced23e96834c37bc36937252c5f36fcb012cd581b4f87cccd8cefbe0dcbd2ce7
The user of MICROSAR Safe shall ensure that the correct implementation method has been chosen for every exclusive area.
Exclusive areas can be used to ensure data consistency (see SMI-11).
The implementation depends on the requirements of the application and on other factors like the expected duration of the exclusive area. Interrupt locks are typically faster than resources but can only be used for short sequences. OS_INTERRUPT_BLOCKING only blocks the interrupts of the operating system whereas ALL_INTERRUPT_BLOCKING blocks all interrupts.
Verification can e.g. be performed by review, static code analysis and/or integration testing.
The RTE Analyzer lists the exclusive areas and their implementation method to assist in this integration step.
- ForeignTraceId: SMI-2122
- ForeignAlternativeId: SMI-378E7CD8-6BB8-4679-A234-213364641919
- ObjectType: RQM_SAFETY_MANUAL_ITEM

##### 10e7b47bf79adfeadb3967018c4e097d43be13618d4ea6198cf17a9e47c1effc: SWC Communication
- ChapterNumber: 11.3.1.3
- ObjectType: DocItem

###### 613efd1ce2aca1c97540ef1114bbfdaeee45cf16e526008747d85cc3f837542e
The user of MICROSAR SafeBRE shall provide the RTE APIs for systems without RTE.
MICROSAR Classic Basic Runtime Environment (BRE) only provides the BSW scheduler functionality of the RTE and does not support application SWCs. The implementation of the interface from the application to BSW modules must be developed according to ISO 26262. The Technical References of the BSW modules as well as the AUTOSAR standard define the semantics and APIs that will have to be implemented while integrating the BRE.
The RTE Analyzer does not assist in this integration step.
- ForeignTraceId: SMI-41492
- ForeignAlternativeId: SMI-BA48C55B-BB21-4DD0-B270-572CF9EE829E
- ObjectType: RQM_SAFETY_MANUAL_ITEM

###### 9afa97cd38fd70841076c3f582ddadab7e625f973ef6d43b422a003410fd009b
SMI-324, SMI-2065 and SMI-2123 do not apply to MICROSAR SafeBRE.
- ObjectType: DocItem

###### 52bb830b18e1b152904dfc0f505547f45149ab56ae3d16dd8afb34b0d55e981c
The user of MICROSAR Safe shall ensure that the connections between SWCs are as intended.
Many types of faults can lead to a mix of connections between SWCs. These are unlikely and usually already addressed by straight-forward integration testing.
The list of senders needs to be correct for every receiver and the subset of the received data needs to be correct. For implicit communication also the buffering in the RTE needs to be considered.
Vector recommends the following RTE subset for safety-related SWCs:
- use only 1:1 or 1:N connections.
- use the same datatype on both sides of a connection
- avoid data conversion
Information that is used from non-safety-related SWCs has to be checked for plausibility. If such a data path is found during integration, this is an indicator that your safety analysis has to be reconsidered. Please note that also other code in the same partition as the non-safety-related SWCs can corrupt the communication if freedom from interference with regards to memory is not ensured.
Moreover a mismatch between the SWC implementation and the configuration that is seen by the RTE generator when it comes to the argument direction of client-server arguments may lead to wrong input and output values.
Verification can be performed by review and/or an integration test testing the normal operation.
The RTE Analyzer list the connections between SWCs to assist in this integration step.
- ForeignTraceId: SMI-324
- ForeignAlternativeId: SMI-DFBF2B85-70A7-4E01-9732-30D018474E7F
- ObjectType: RQM_SAFETY_MANUAL_ITEM

###### 7a254761012c3785c762df9510ed27efac3901b371a180df9b645971d7ac3398
The user of MICROSAR Safe shall ensure that inter-ECU sender-/receiver and inter-ECU client-/server communication work as expected.
This requires verification of:
- data needs to be routed to the correct ECU by the underlying communication stack. This includes 1:1, 1:N, N:1 and reception of partial signal data.
- both ECUs need to use the same data representation (datatypes, endianness, serialization)
Vector requires using E2E protection for safety-related signals.
Only evaluating the status information from the COM (e.g. update, alive timeout, invalidation status) is no sufficient safety menchanism.
Vector requires not using Inter-ECU client-server communication for safety-related signals.
Vector requires not using Inter-ECU trigger communication for safety-related signals.
Vector requires not using implicit communication for safety-related signals.
Vector requires not using blocking queued communication for safety-related signals.
Vector requires not using LDCOM trigger transmit for safety-related signals.
Vector requires not using queued communication with TP signals for safety-related signals.
Vector requires not using invalidation for safety-related signals.
Vector requires not using scaling for safety-related signals.
Vector requires not using read by value for safety-related signals.
Vector requires that other software does not corrupt RTE variables in the BSW partition when client or server use E2E protection and are not located in the BSW partition. This is necessary because the transformers including the E2E transformer need to be called in the BSW partition in order to route signals to the requesting component.
Vector recommends using 1:1 connections.
Vector recommends always sending and receiving complete data elements.
Integration testing on vehicle network level using fault-injection can be used. Vector assumes that this is normally done to verify the effectiveness of the E2E protection.
Testing needs to be performed for all postbuild variants.
The RTE Analyzer lists the APIs of SWCs with inter-ECU communication to assist in this integration step.
- ForeignTraceId: SMI-2065
- ForeignAlternativeId: SMI-0E4C9567-FD66-41DD-97DF-CC896E710DB8
- ObjectType: RQM_SAFETY_MANUAL_ITEM

###### 92f2d39cd9260e708697ae6d59c252a266ed15431f9b4d0b53c8f3bc19f789c0
The user of MICROSAR Safe shall ensure that all connected SWCs expect the same converted data.
The RTE offers conversions that can be applied to specific connections.
Vector recommends not using data conversion for safety-related connections.
Verification can e.g. be performed by review or integration testing of all data conversions.
The RTE Analyzer lists all APIs of SWCs that perform data conversion to assist in this integration step.
- ForeignTraceId: SMI-2123
- ForeignAlternativeId: SMI-2B7C2675-E792-4831-9EDD-E6A22FB4CF2F
- ObjectType: RQM_SAFETY_MANUAL_ITEM

##### 7d159c06858a63afbdd977b4f2ce3e7819c56105c759c9a59b92585826f060d3: Usage of RTE Headers
- ChapterNumber: 11.3.1.4
- ObjectType: DocItem

###### 09f3baa684ad45c632a01bd1bb29f39025a36712da3552e54585e02b42c2ad27
The user of MICROSAR Safe shall ensure that the defines and typedefs that are generated by the RTE match the expectations of the SWCs that use them.
Inconsistencies may lead to e.g, memory corruption when a runnable uses an RTE array datatype within its implementation and writes beyond the bounds of this array.
Moreover, different SWCs may have different assumptions with regards to the meaning of communicated values, e.g. if one SWC uses the symbolic name, another SWC the integral value of an enumerated type.
The following code is provided:
- Configured Application Error Defines for Client-/Server Communication
- Configured AUTOSAR Datatypes
- Configured Upper and Lower Limit Defines for Primitive Application Data Types
- Configured Init Value Defines for Sender-/Receiver Communication
- Configured InvalidValue Defines for Sender-/Receiver Communication
- Configured Enumeration Defines for CompuMethods
- Configured Mask Defines for CompuMethods
- Configured Mode Defines for Mode Communication
- Configured ActivationReasons
- Configured Rte_IsAvailable and Rte_SetAvailable defines for records with optional elements
The defines and typedefs are part of the Rte_Type.h, Rte_<SWC>.h and Rte_<SWC>_Type.h headers.
Vector recommends using the headers generated by the RTE when a static code analysis is performed on the application code.
Vector recommends only using the defines instead of the defined values in the code.
Vector recommends using the defines only when needed (Mode, Application Error Defines).
Vector recommends reviewing the used defines for safety-related SWCs.
Vector recommends not using union types in the SWCs.
Verification for correct usage of datatypes may be performed by review and/or static code analysis. Consistent usage of defines can be verified by review and/or integration testing with all used values.
The RTE Analyzer verifies that all accesses within the RTE do not lead to memory corruption.
- ForeignTraceId: SMI-2067
- ForeignAlternativeId: SMI-E173ED0C-016B-4D64-A579-F24D8BFE3F1C
- ObjectType: RQM_SAFETY_MANUAL_ITEM

###### 01e59d97cb5a7563c8248105fd5ba430b73bfa95cf1edf524bc6cb00f5ee8ac0
The user of MICROSAR Safe shall ensure that the indirect API is used consistently.
Indirect API functionality consists of the APIs:
- Rte_Port
- Rte_Ports
- Rte_NPorts
The indirect API makes it possible to call different APIs through an array access. The indirect API functionality can be enabled individually per port.
A wrong configuration switch can easily lead to a call outside of the array returned by the Rte_Ports API.
Vector recommends not using the indirect API.
Verification can e.g. be performed by review that the intended APIs are returned.
The RTE Analyzer does not assist in this integration step.
- ForeignTraceId: SMI-2071
- ForeignAlternativeId: SMI-9771D856-2E2F-44A2-A944-6F30EBD7BC8D
- ObjectType: RQM_SAFETY_MANUAL_ITEM

##### 07311e63f1daf194a2bae05ed192a55f5ef24bcec43b596984a5d2cd54acc1d6: Usage of RTE APIs
- ChapterNumber: 11.3.1.5
- ObjectType: DocItem

###### 99eef1bd5989c3832c85624362c22ddf3578901ad60c5e21d11ec747ce224401
The user of MICROSAR Safe shall ensure that the RTE and all of its users have the same assumptions with regards to the sizes of the datatypes.
The RTE supports the configuration of custom datatypes for its APIs. The RTE specification mandates that arrays are passed as pointer to the array base type.
The RTE does not enforce that both sides of a connection use arrays of the same size.
No NULL pointers or invalid pointers shall be passed to RTE APIs.
As an exception NULL pointers can be passed to IN arguments of client-server operations that use a data type of category data reference.
The object to which the pointer points needs to have at least the size of the pointer base type.
No variables from ASIL partitions shall be passed as out parameters to RTE APIs in QM partitions.
RTE APIs returning a pointer/reference need special care:
- Use correct data-type/data-size for reading or writing.
- Use the pointer/reference only during execution of the runnable and within its scope.
- Do not globally store retrieved pointers, they might not be valid after runnable execution.
Vector recommends using the headers generated by the RTE when static code analysis is performed on the application code.
Vector recommends using the same datatypes on both sides of a connection.
Arrays and void pointers on interfaces where the called function writes to them are considered especially relevant.
Verification can e.g. be performed by review and/or static code analysis.
The RTE Analyzer lists APIs and runnables that use such parameters to assist in this integration step.
- ForeignTraceId: SMI-2072
- ForeignAlternativeId: SMI-EEDAE939-E775-466C-9D90-69C684B1D655
- ObjectType: RQM_SAFETY_MANUAL_ITEM

###### 6823a99ea19d8545f577f02c70ac08722e895bf1e6608b7f6b7ee2160e798580
The user of MICROSAR Safe shall ensure that RTE APIs are only called from their configured contexts.
Fast response times are crucial in embedded systems. Therefore, the RTE generator analyzes the call contexts of all APIs in order to optimize away unneeded interrupt locks. When the application calls the APIs from a different context than the RTE assumes, data consistency problems may arise.
In systems with ASIL partitions, the RTE generator uses a conservative locking strategy unless this is explicitly disabled with the parameter OptimizeLocksInASILPartitions. Locks are only optimized away if all accesses are done within the same task.
Verification can e.g. be performed by review and/or static code analysis.
The RTE Analyzer lists the optimized APIs of SWCs to assist in this integration step.
The RTE Analyzer lists APIs that must not be called by the application because they are considered unreachable due to the RTE configuration.
- ForeignTraceId: SMI-2073
- ForeignAlternativeId: SMI-7C4129D2-4810-4249-8027-3A3E080DFBEC
- ObjectType: RQM_SAFETY_MANUAL_ITEM

###### 266710cea02afedc2f8b3c72a3c2f48e817cec4e0195f9a09582f72303a49d4c
The user of MICROSAR Safe shall ensure that implicit accesses with RteExclusiveAccessOptimization are really exclusive.
RteExclusiveAccessOptimization containers can be configured to mark implicit accesses to NV block SWCs as exclusive. As the RTE generator does not implement any data consistency mechanisms for such accesses, RteExclusvieAccessOptimization must only be configured in case the RAM mirror is not accessed concurrently in the target system.
Verification can e.g. be performed by review.
The RTE Analyzer lists concurrent accesses to the RAM mirror of NvBlockSWCs as if RteExclusiveAccessOptimization was not configured.
- ForeignTraceId: SMI-859695
- ForeignAlternativeId: SMI-4678A31F-905A-42A7-9017-90BB58FE3FF7
- ObjectType: RQM_SAFETY_MANUAL_ITEM

##### f0bc5c1a17b6c1e6ed56e3a1faaf1bb2019630bfd15cd910f86a013a9151155d: Configuration of RTE APIs
- ChapterNumber: 11.3.1.6
- ObjectType: DocItem

###### 56a90a6c912827283762b78cdb0692c0911954d57ea66405184e715141fe7cd9
The user of MICROSAR Safe shall ensure that the receivers can handle the initial value provided by the RTE if no write or calibration occurred.
For implicit accesses the user of MICROSAR Safe shall assure that the correct initial value is sent when Rte_IWrite or Rte_IWriteRef were not called in the runnable.
Initial values can be configured for:
- non-queued sender-/receiver communication
- inter-runnable variables
- mode ports
- calibration parameters
- per-instance memories
The initial value is returned when no sending API was called before the first read or no calibration was performed before the first read. The initial values depend on the connected components.
Vector recommends using the same initial value on all port data elements that are connected with each other.
The RTE Analyzer lists all APIs of SWCs that may provide an initial value to assist in this integration step. If possible, the RTE Analyzer reports the initial value generated by the RTE into the configuration feedback report.
- ForeignTraceId: SMI-2074
- ForeignAlternativeId: SMI-8ECC3F89-9B74-47C2-AD0D-C2275107C1A2
- ObjectType: RQM_SAFETY_MANUAL_ITEM

###### 46804fbb872925694d2deb1340d58bf61f32f20c7f1f80d40b12ef89321a7826
The user of MICROSAR Safe shall ensure that the alive timeout by the COM is not used for safety-related inter-ECU sender/receiver communication.
Safety-related communication must be protected by E2E protection. The decision if new data is available (alive) can only be made by the E2E mechanism. Data is not interpreted by the COM. For example the sending ECU might repeat old data. This is only detected by the cycle counter that is part of the E2E protection.
The RTE Analyzer lists the reading APIs that provide the alive timeout status to assist in this integration step.
- ForeignTraceId: SMI-2075
- ForeignAlternativeId: SMI-9C53929B-9909-457C-9D8A-A96D969D6C83
- ObjectType: RQM_SAFETY_MANUAL_ITEM

###### 1fc54bfeeaf43fa8ed0fcba7e8e5488d81b71c21eac67191660743037b73258f
The user of MICROSAR Safe shall ensure that SWCs handle the RTE_E_INVALID return code properly.
The RTE offers a functionality to invalidate signals.
Vector requires using end-to-end protection for safety-related inter-ECU communication. Relying on the invalidation mechanism for safety-related signals is not an option. The user of MICROSAR Safe shall not use invalidation for inter-ECU communication.
Verification can e.g. be performed by review and/or integration testing.
The RTE Analyzer lists RTE APIs that return the RTE_E_INVALID return code to assist in this integration step.
- ForeignTraceId: SMI-2126
- ForeignAlternativeId: SMI-B5D13C34-98C3-42A9-AFE8-B3DC17F2861D
- ObjectType: RQM_SAFETY_MANUAL_ITEM

###### 7057a5ea907750a926b44bcbb061b0fff63df753390573ba80ae0094620a5ff6
The user of MICROSAR Safe shall ensure that SWCs handle the RTE_E_NEVER_RECEIVED return code properly.
The RTE offers a functionality to report if a signal was received after the ECU was started.
Vector requires using end-to-end protection for safety-related signals. Relying on the never received mechanism for safety-related signals is not an option. Especially, when using the E2E transformer, its return value shall be evaluated.
Verification can e.g. be performed by review or integration testing.
The RTE Analyzer lists RTE APIs that return the RTE_E_NEVER_RECEIVED return code to assist in this integration step.
- ForeignTraceId: SMI-2127
- ForeignAlternativeId: SMI-9934B596-45F2-4913-9F0D-B31ED25FBA92
- ObjectType: RQM_SAFETY_MANUAL_ITEM

###### 2240580a104623c2f2e6240b644a0ab8c2fdd76321848c23ad7e0ee0f5232035
The user of MICROSAR Safe shall ensure that the queue sizes that were chosen during the configuration are sufficient for the integrated system.
The RTE uses queues for mode communication, sender-/receiver communication and mapped client-/server communication. The queue sizes depend on the scheduling of entities and the call sequences of the APIs.
The queue handling code for server runnables and mode switches is executed in a loop in the task.
Adding new data while the queue is processed leads to additional loop iterations.
The RTE uses the configured queue sizes to limit the number of queue entries that are processed at once when the server runnable is triggered so that other entities in the same task and tasks with higher priority can be scheduled in between.
Still, entities in tasks with lower and equal priority may be blocked until the queue is empty. This needs to be considered when designing fail-operational systems. All partitions need to be analyzed for fail-operational systems, not only the ASIL partitions.
Vector recommends not using APIs with queues for safety-related functionality.
Vector requires not using queues with more than 1000000 elements for safety-related functionality.
Verification can e.g. be performed by stress testing.
The RTE Analyzer lists the queue sizes to assist in this integration step.
- ForeignTraceId: SMI-2125
- ForeignAlternativeId: SMI-21098D07-79AA-43E6-B240-760BFAF0D989
- ObjectType: RQM_SAFETY_MANUAL_ITEM

###### a563f34dc1266ad32ddf687c8478e940bda38f8ca46f7390960cb68aeecc7a63
The user of MICROSAR Safe shall ensure that all connections with end-to-end (E2E) protection are generated.
The RTE Analyzer lists RTE APIs that read or write end-to-end protected data (see SMI-98).
- ForeignTraceId: SMI-36068
- ForeignAlternativeId: SMI-E52B3575-C987-4004-BAC2-05C7876F64A4
- ObjectType: RQM_SAFETY_MANUAL_ITEM

###### f10248d00f1a26f3dab7d482c7e615063dc08505482671873b642bce907ef111
The user of MICROSAR Safe shall ensure that the generated code with activated illegal invocation detection is not used in ASIL Software.
The RTE offers a functionality to detect RTE API Calls called by a Runnable which should not call the RTE API according to the Runnables contract and report those to the DET.
This functionality is intended to be only used as a checking mechanism to ensure that the RTE APIs are used as configured.
Using this functionality in production software could have negative impact in the overall time behaviour of the system, as a check is performed for every call to one of the RTE APIs, that are configured to be checked.
Vector recommends not using the illegal invocation detection for safety-related functionality.
- ForeignTraceId: SMI-1093171
- ForeignAlternativeId: SMI-79634756-B357-4BA0-B234-FF1B4A0A1241
- ObjectType: RQM_SAFETY_MANUAL_ITEM

### 1062ba369043247598b7d429d39ce38599d1f1622524c86ea52b56d2836bc4db: Safety requirements required from other components
- ChapterNumber: 11.4
- ObjectType: DocItem

#### d89fb5274affd53598292b4085da62d62a1cbd5d047482b353251b97b0a57335
The RTE requires the following functionality as safety requirements from the operating system:
- Interrupt enabling/disabling (TSR-101876)
- Resource handling (TSR-101876)
- Inter OS Application Communicator (IOC) sending and receiving functionality (TSR-12)
- Spin-lock functionality (TSR-101876)
- Alarm handling (TSR-6)
- Core handling (TSR-6)
- Counter handling (TSR-6)
- Schedule table handling (TSR-6)
- Activation of tasks (TSR-6)
- Event handling (TSR-6)
For components provided as part of MICROSAR Safe, the respective section of the Safety Manual for that component allows you identifying if this requirement is fulfilled.
- ForeignTraceId: SMI-2121
- ForeignAlternativeId: SMI-5EBFCAC5-77AC-4288-9DE5-B128DBA04F65
- ObjectType: RQM_SAFETY_MANUAL_ITEM

#### 645e6d8de678f853555b697b78a3652d24cb8d3d20e4e41012d1ccfff777b25b
The RTE requires the following functionality as safety requirements from the NVM:
- Reading blocks (TSR-5)
- Writing blocks (TSR-4)
For components provided as part of MICROSAR Safe, the respective section of the Safety Manual for that component allows you identifying if this requirement is fulfilled.
This requirement only applies if TSR-4 and TSR-5 are considered a safety requirement.
- ForeignTraceId: SMI-2978
- ForeignAlternativeId: SMI-3DB2079A-28B9-48A3-8066-032CD0DBB470
- ObjectType: RQM_SAFETY_MANUAL_ITEM

#### 87a140a6abeec0bc9d50e27c87fe650030e8ac817c0535c68e7c9a8371d8f6c1
This component requires sending and receiving functionality as an assumed safety requirement (TSR-111108) from other interfacing components.
For components provided as part of MICROSAR Safe, the respective section of the Safety Manual for that component allows you identifying if this requirement is fulfilled.
This requirement is only applicable if TSR-111108 is assumed as a safety requirement.
- ForeignTraceId: SMI-661323
- ForeignAlternativeId: SMI-DDBCA963-96A3-4CDA-BEF9-C2D20B2037E0
- ObjectType: RQM_SAFETY_MANUAL_ITEM

### 032030f520c32383d860688c3ee67f77ead7aa6cd661e21c05d9db2403c69cba: Dependencies to hardware
- ChapterNumber: 11.5
- ObjectType: DocItem

#### 823950e4e9ad91f95bc4a434f19603819eaf569ce9753c80509b7b79c5e050f8
This component does not use a direct hardware interface.
- ObjectType: DocItem

## 9d458692b6777f95dff163aad22a418df3df92e73e5dd0ba85ce672093e20349: Safety Manual VStdLib
- ChapterNumber: 12
- ObjectType: DocItem

### 5007e9d48e996ae1826dda2603e3a8b6f30cd550e337aefc1c115773ae03ced0: Assumed safety requirements
- ChapterNumber: 12.1
- ObjectType: DocItem

#### f95585b1d719f6eb189cd19edf73abd97a78a6a3927a0f76c567ef2c5c8beb7a
This component assumes the following safety requirements:
| ID | Safety Requirement | Associated TSR | ASIL |
| --- | --- | --- | --- |
| CREQ-VStdLib-MemoryInitializationZero | VStdLib_GenericAsr shall provide a service to initialize memory to zero. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-MemoryInitializationPattern | VStdLib_GenericAsr shall provide a service to initialize memory to a specified pattern. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-MemoryCopy | VStdLib_GenericAsr shall provide a service to copy data from one memory location to another. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-MemoryCopyEndianConversion | VStdLib_GenericAsr shall provide a service to copy data from one memory location to another with a converted endianness. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-MemoryComparison | VStdLib_GenericAsr shall provide a service to compare two memory areas. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-MemoryComparisonPattern | VStdLib_GenericAsr shall provide a service to check that a memory area contains only a specified pattern. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-BitSearch | VStdLib_GenericAsr shall provide a service to search for the highest/lowest set/unset bit in different sized unsigned integers. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-Serialization | VStdLib_GenericAsr shall provide a service to serialize differently sized integers to a byte stream. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-Deserialization | VStdLib_GenericAsr shall provide a service to deserialize a byte stream to differently sized integers. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-EndianSwap | VStdLib_GenericAsr shall provide a service to swap the endianness of differently sized integers. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-EndianConversion | VStdLib_GenericAsr shall provide a service to convert differently sized integers from the platform endianness to big/little endian and vice versa. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
| CREQ-VStdLib-BitCopy | VStdLib_GenericAsr shall provide a service to copy data from one memory location to another where the amount of data to be copied is specified in bits. | TSR-1, TSR-4, TSR-5, TSR-6, TSR-7, TSR-8, TSR-9, TSR-10, TSR-12, TSR-13, TSR-14, TSR-15, TSR-16, TSR-17, TSR-18, TSR-100551, TSR-101876, TSR-111108, TSR-111109 | ASIL D |
The above listed TSRs apply to the Vector implementation (functions and macros) and not to externally defined implementations like, e.g., compiler intrinsics or user implementations.
This component in addition to the assumed safety requirements ensures freedom from interference with respect to memory and timing with up to ASIL D.
- ObjectType: DocItem

### b403076aec64a7b26c9076d3b21741cb776352eb73d335244d876e1b6686eacc: Configuration constraints
- ChapterNumber: 12.2
- ObjectType: DocItem

#### b769bf5c0d02f83c6c4b0b9137720e5ae5aa19e85d7e8c4631fc9701e73bd3fa
This component does not have configuration constraints.
- ObjectType: DocItem

### 0eba986ff85bbf789a7fea6859ca5d2abc9a5c727ce83303290408dbc5b748e6: Additional verification measures
- ChapterNumber: 12.3
- ObjectType: DocItem

#### 59e4871146193b7794d0424bfa75b82eb0836ec7e12f141fd3b6c2e13eff3bae
This component does not require additional verification measures.
- ObjectType: DocItem

### 648a071bb5c7833d920208da1da0b3a62732a955023673e5dbfbdd7a11f1e994: Safety requirements required from other components
- ChapterNumber: 12.4
- ObjectType: DocItem

#### d9c0dec0977a295287cd675364158933d33148a76b899a82b493db906b887814
This component does not require safety requirements from other components.
- ObjectType: DocItem

### cbcd2090827f092a37fe2c640741b6d279bd783e42cb3d565e914ce85be92761: Dependencies to hardware
- ChapterNumber: 12.5
- ObjectType: DocItem

#### 3f3c3632bc65e1d8ae183e91c13ba275d3573448588d2596296664ea4e3d9a8a
This component does not use a direct hardware interface.
- ObjectType: DocItem

## ffa54ef684ccb4cda65c6004f548cf1f89dd67a0f509f1ee4f51bb1b53c80238: Safety Manual Wdg
- ChapterNumber: 13
- ObjectType: DocItem

### 4bca7c3d5f86a1bc1fe8ea3750313230b0d51d04b591641a4acbc762163bbfe9: Safety requirements
- ChapterNumber: 13.1
- ObjectType: DocItem

#### 5251d1f1c737b6ccac762ecbe18ca309ac62d02217dc72fbc96543c26cd834b2
This component provides the following safety requirements:
| ID | Safety requirements | Linked TSR |
| --- | --- | --- |
| CREQ-105559 | Wdg shall provide a service to initialize itself and the watchdog hardware. | TSR-13,TSR-14,TSR-15 |
| CREQ-105560 | Wdg shall provide a service to set the watchdog mode. | TSR-13,TSR-14,TSR-15 |
| CREQ-105561 | Wdg shall provide a service to set trigger condition. | TSR-13,TSR-14,TSR-15 |
| CREQ-105563 | Wdg shall provide a service that triggers the watchdog hardware if trigger condition is valid. | TSR-13,TSR-14,TSR-15 |
| CREQ-106194 | Wdg shall provide an OFF mode. | TSR-13,TSR-14,TSR-15 |
| CREQ-106195 | Wdg shall provide a SLOW mode. | TSR-13,TSR-14,TSR-15 |
| CREQ-106196 | Wdg shall provide a FAST mode. | TSR-13,TSR-14,TSR-15 |
- ForeignTraceId: SMI-279
- ForeignAlternativeId: SMI-8EFC4C95-2526-4F24-B56E-39A71272C34A
- ObjectType: RQM_SAFETY_MANUAL_ITEM

### 2d65b640ad588608216ffaefbb26fe4b1614e46a4b91ca99c6d61076f5c3f425: Configuration constraints
- ChapterNumber: 13.2
- ObjectType: DocItem

#### 53ede23729a688523d9e249aa0fcc1eeaad5e35c6891156c428860ff6ecc3459
This component does not have configuration constraints.
- ObjectType: DocItem

### f30d50390365418660e0d8ea501f769cd317340fbd3b1d389c4e50d7b4343de5: Additional verification measures
- ChapterNumber: 13.3
- ObjectType: DocItem

#### d9a0382715d4569cbefe5705e9a5b06cb219b789f0e1479cdd56f5f6827dd435
The user of MICROSAR Safe shall verify that the Wdg driver is only initialized at intended points in time, e.g. during initialization.
Unintended re-initialization may lead to a disabled watchdog.
- ForeignTraceId: SMI-253
- ForeignAlternativeId: SMI-E386B2AD-3AEC-4B9B-A508-EC39AC851BD6
- ObjectType: RQM_SAFETY_MANUAL_ITEM

#### 415ed98f5cccca1e2482b6360c699e013608f2f57e0a38247710a1ed75578bb5
The user of MICROSAR Safe shall verify that the Wdg driver services are only called by the watchdog interface.
This requierment does not apply to the service for initalization and the interface to Gpt (general purpose timer).
This requirement is fulfilled for all components of MICROSAR.
If e.g. the trigger condition is extended by another component, this may lead to unintended triggering of the watchdog.
- ForeignTraceId: SMI-254
- ForeignAlternativeId: SMI-85FC31AC-E49C-46E1-B854-333ED063BD19
- ObjectType: RQM_SAFETY_MANUAL_ITEM

### a97dbd895fe7ca963597be8eb583471cd5aed1856ff162cad9e4bad9357443c5: Safety requirements required from other components
- ChapterNumber: 13.4
- ObjectType: DocItem

#### 7bfe0284985771ba78a40881f455583cb73006db32202a395801c8e582b2f7fa: Safety features required from other components
- ChapterNumber: 13.4.1
- ObjectType: DocItem

##### d1d2f083bdda7f0f7a9694821e78816983b87251edef06e480a6559611dc66da
The Wdg interface shall call the service to set the mode and the trigger condition as expected by the Wdg driver.
This requirement is fulfilled if the watchdog interface and manager by Vector is used.
If the watchdog is not properly set up, it may not provide the expected protection.
- ForeignTraceId: SMI-255
- ForeignAlternativeId: SMI-433E69D8-D815-4FF2-9C12-05ED80088798
- ObjectType: RQM_SAFETY_MANUAL_ITEM

#### 3e89b3cbc4ff977ae6a5ad0912bd72b9c8a9cba3063221bd74619509109c01a4: Coexistence with other components
- ChapterNumber: 13.4.2
- ObjectType: DocItem

##### 8226a33ffe1df49f1b4c06854bbd9f9dd031ca8021c294824726b4e77cc56dcd
This component requires coexistence with Det, Dem, Dio, Spi, Sbc and Gpt components if the interface for those components is configured.
This requirement is fulfilled if components from Vector are used.
- ForeignTraceId: SMI-280
- ForeignAlternativeId: SMI-8132510E-B43A-4BE5-AAF8-C7319052E3DA
- ObjectType: RQM_SAFETY_MANUAL_ITEM

### b1b757aeeb5b6fdd63977824d403467dd6dc3ff6975f83693946e92d54a66106: Dependencies to hardware
- ChapterNumber: 13.5
- ObjectType: DocItem

#### 33331fea4530c0686ec97db535c78a3981e20e228f4919ccc7e13aaedab50931
The hardware interface is described in the Safety Manual of the low-level part of the Wdg driver.
- ObjectType: DocItem

## ea8ba97e79195d509620ba94cc0b7d0709ed7e1f77ea2d89a0d91672d120f84b: Safety Manual Wdg (DrvWd_XTle4278gEAsr)
- ChapterNumber: 14
- ObjectType: DocItem

### c67252f5f79665c214b75ef47d0e072f25ea03c6528514c75795525d2d081417: Safety features
- ChapterNumber: 14.1
- ObjectType: DocItem

#### 07e6222fcf5fa873714bcc569046cc2cdf755a122e62d6ac910eeebeb2b5e0f2
No additional safety features are provided for DrvWd_XTle4278gEAsr.
- ObjectType: DocItem

### b3ea64a21270f507f03c8e475b38c400b2badc3e6fe9965eaffd8009244bc6a5: Configuration constraints
- ChapterNumber: 14.2
- ObjectType: DocItem

#### 1678522f90b9994ddaef00d4bf5def5768c71428b36e8d45d29e3ac7da1503ad
No additional configuration constraints are required.
- ObjectType: DocItem

### 38e1b41acdca37e6fe3df770d7ef0477937fbd2397422adf2e9f33b54414bbf0: Additional verification measures
- ChapterNumber: 14.3
- ObjectType: DocItem

#### 3cdab795d17ce3fd36a809d46401cf7d1d3f77740cca3a5164fac13e99e3b546
No additional verification measures are required.
- ObjectType: DocItem

### 80be5e04feeaa44269c42e8b79b2d45d7946ba3781258317f2aac824d7b8340d: Dependencies to other components
- ChapterNumber: 14.4
- ObjectType: DocItem

#### 33515c4be57998c09596dc6a3da130fc2c43c31d52923d803841d29feb61e815: Safety features required from other components
- ChapterNumber: 14.4.1
- ObjectType: DocItem

##### cd59916102c02200b8279303e41c38def6d417e89bced46b67203fe4474b3349
The Dio driver shall provide the DIO channel read service and the DIO channel write service as a safety feature.
This requirement is fulfilled if components from Vector are used.
- ForeignTraceId: SMI-2676
- ForeignAlternativeId: SMI-AB550F3D-FB2D-477E-9973-B42CC5304B29
- ObjectType: RQM_SAFETY_MANUAL_ITEM

#### 3a951707bb8b63e8ed9cde14c17031140320ccb8f6ee486a59924d767fada580: Coexistence with other components
- ChapterNumber: 14.4.2
- ObjectType: DocItem

##### 998c7d0c3665f083e5f2c5911f28287a730b2658b70e6d3baa061c28db5e8afc
No additional coexistence with other components is required.
- ObjectType: DocItem

### b72242cfc920d34455e91ed803ad18f320fbc3169fbc94afad2368e4d88437cb: Dependencies to hardware
- ChapterNumber: 14.5
- ObjectType: DocItem

#### f24038133883bd819260caec3427d286c55c142186a165528d842a7bde31ce4c
This component does not use a direct hardware interface. The Dio driver is used to access the hardware watchdog unit.
- ObjectType: DocItem

## 287bc1e5fffd6d7931d46f0fb8b11829f24044a9a6e788c754f0c853eb0e3f5d: Safety Manual WdgIf
- ChapterNumber: 15
- ObjectType: DocItem

### ada976bf738104de97471ba318a6d662b46e7c680f034f67706dadb72cc42611: Assumed safety requirements
- ChapterNumber: 15.1
- ObjectType: DocItem

#### 0f92b89d335f76a808528518eae5c95a76bbe3a1514786abc7fb541101f6733e
This component assumes the following safety requirements:
| ID | Safety Requirement | Associated TSR | ASIL |
| --- | --- | --- | --- |
| CREQ-107414 | WdgIf shall provide a service to set the mode of a watchdog device | TSR-13,TSR-15,TSR-14 | ASIL D |
| CREQ-107415 | WdgIf shall provide a service to set the trigger condition for a watchdog device | TSR-13,TSR-15,TSR-14 | ASIL D |
| CREQ-107416 | WdgIf shall support a mechanism to combine statuses of different cores and handle one watchdog for different cores | TSR-13,TSR-14,TSR-15 | ASIL D |
This component in addition to the assumed safety requirements ensures freedom from interference with respect to memory with up to ASIL D.
- ForeignTraceId: SMI-519
- ForeignAlternativeId: SMI-8EB270D4-BC73-43CD-83DF-6C3A7055E825
- ObjectType: RQM_SAFETY_MANUAL_ITEM

#### 865d81594e9482e9bdc426137e3548c601ed40cf1f9f4bc14dd50899361551fc
Hint: This component does not offer an init function.
- ObjectType: DocItem

### 3b3dce3ef67c2ef652ef21f2528a0e138ef30144e6da47bd8d57eca9864ead7f: Configuration constraints
- ChapterNumber: 15.2
- ObjectType: DocItem

#### bbe7631a5b7b110dc6e8315ac14402064354c1e8750df3617fef8c62385f16cc
If a state combiner is used, the user of MICROSAR Safe shall configure
- WdgIfStateCombinerOSSpinlock or WdgIfStateCombinerSpinlockID and
- WdgIfStateCombinerStartUpSyncCycles
for each core that is used by the state combiner.
- ForeignTraceId: SMI-522
- ForeignAlternativeId: SMI-31835737-1707-4683-8079-74005C275216
- ObjectType: RQM_SAFETY_MANUAL_ITEM

#### 79eda20f58ead3eb78da25b0dd49ef8b4a7ab60a824e44bd2df55a45ae0c25aa
If a state combiner is used and WdgIfStateCombinerStartUpSyncCycles is set to a value s, the user of MICROSAR Safe shall consider that for the first s SupervisionCycles of the master, the master does not monitor the slave triggers.
However, reset requests from a slave within the first s SupervisionCycles, are escalated by the master with the next call of the master’s WdgM_MainFunction().
- ForeignTraceId: SMI-523
- ForeignAlternativeId: SMI-A3306ABD-9E06-41D0-8704-2AA5EC1F9286
- ObjectType: RQM_SAFETY_MANUAL_ITEM

### b107da524d28f435d2354aa4f149aad288b9fe66fd65cb816d8cc3835a22fc45: Additional verification measures
- ChapterNumber: 15.3
- ObjectType: DocItem

#### 8a9e86d6b35b1ab080780a592052000a579af6d6653fc34d33ef26c3399a9315
The user of MICROSAR Safe shall verify that the output path of the generator is empty before the generator is started.
The output path can be defined by the command line argument OUTPUT-DIRECTORY.
- ForeignTraceId: SMI-525
- ForeignAlternativeId: SMI-090E7D86-3C15-4994-8D19-24F32098A625
- ObjectType: RQM_SAFETY_MANUAL_ITEM

#### aeeebeb915981527756087edcfe478e79455489d684fe996aa8066edbb0ec055
The user of MICROSAR Safe shall inspect the messages of the generator execution.
If the generator aborts the generation process with an error message, the (partially) generated output files shall not be used in the system.
If the generator detects an error, a message starting with "ERROR" is displayed on the standard output.
If the generator shows a warning message starting with "WARNING", the user of MICROSAR Safe shall ensure that the cause of the warning does not invalidate the generated output files.
- ForeignTraceId: SMI-526
- ForeignAlternativeId: SMI-6C3240BE-65E1-4A80-8777-8550E1153EB7
- ObjectType: RQM_SAFETY_MANUAL_ITEM

#### 5baf5ce3408e84746aaf863ff902787abec816c72ff3248a9ba9c6abb2f0ad38
The user of MICROSAR Safe shall verify that the following preprocessor directives are defined with the correct value independent from whether a state combiner is configured or not:
| Preprocessor Directive | Value |
| --- | --- |
| WDGIF_VERSION_INFO_API | STD_ON if WdgIfVersionInfoApi is TRUE, otherwise STD_OFF. |
| WDGIF_DEV_ERROR_DETECT | STD_ON if WdgIfDevErrorDetect is TRUE, otherwise STD_OFF. |
| WDGIF_USE_STATECOMBINER | STD_ON if WdgIfUseStateCombiner is TRUE, otherwise STD_OFF. |
The defines can be found in WdgIf_Cfg_Features.h.
- ForeignTraceId: SMI-527
- ForeignAlternativeId: SMI-ADBA3884-0817-48B5-98C8-26F6810B3194
- ObjectType: RQM_SAFETY_MANUAL_ITEM

#### d28b398e23503bd004c354484fb58f1a072925d20930ce1394a877b740d60491
The user of MICROSAR Safe shall verify that the following preprocessor directives are defined with the correct value only if a state combiner is configured:
| Preprocessor Directive | Value |
| --- | --- |
| WDGIF_STATECOMBINER_USE_OS_SPIN_LOCK | STD_ON if WdgIfStateCombinerUseOsSpinlock is TRUE, otherwise STD_OFF. |
This define can be found in WdgIf_Cfg_Features.h.
- ForeignTraceId: SMI-528
- ForeignAlternativeId: SMI-5240401B-15F5-437C-A77D-41099182A7A3
- ObjectType: RQM_SAFETY_MANUAL_ITEM

#### 5b6180749bde8108e8a11db5cd3c860277dac4224e8bbf7c421b3c6995b0990c
The user of MICROSAR Safe shall verify that the following preprocessor directives are defined with the correct value independent from whether a state combiner is configured or not:
| Preprocessor Directive | Value |
| --- | --- |
| WDGIF_NUMBER_OF_WDGIFDEVICES | The number of configured WD Interface Devices. |
This define can be found in WdgIf_LCfg.h.
- ForeignTraceId: SMI-529
- ForeignAlternativeId: SMI-E905505A-F626-4BE4-942F-F058D37973D3
- ObjectType: RQM_SAFETY_MANUAL_ITEM

#### b2326f5153c5198eaaaec263858cbca37bbd0d8a08b8ab69bccc89e3c3100a44
The user of MICROSAR Safe shall verify that the following preprocessor directives are defined with the correct value only if a state combiner is configured:
| Preprocessor Directive | Value |
| --- | --- |
| WDGIF_NUMBER_OF_SLAVES | The configured number of slave cores. Cores that are not attached to a State Combiner (i.e. they run independent from other cores) do not count as slave. |
This define can be found in WdgIf_LCfg.h.
- ForeignTraceId: SMI-530
- ForeignAlternativeId: SMI-F8EBCB19-E36E-4AE1-A19C-58F6A1EF2777
- ObjectType: RQM_SAFETY_MANUAL_ITEM

#### 4d8a4431ee59735d14068e527284816f61748501929aba2fd94c699575b57abd
The user of MICROSAR Safe shall verify that the C-struct const WdgIf_InterfaceType WdgIf_Interface is defined in WdgIf_LCfg.c.
WdgIf_Interface shall contain the following fields:
| Field | Value | Description |
| --- | --- | --- |
| 1st | WDGIF_NUMBER_OF_WDGIFDEVICES | The number of WD Interface Devices. |
| 2nd | WdgIf_FunctionsPerWdg | A reference to the list of WD Interface Devices. |
If a state combiner is configured, WdgIf_Interface shall also contain the following field:
| Field | Value | Description |
| --- | --- | --- |
| 3rd | &wdgif_statecombiner_config | A reference to the state combiner data structure. |
- ForeignTraceId: SMI-531
- ForeignAlternativeId: SMI-507F33D3-2FA5-44EC-A18C-34BF84A0AF78
- ObjectType: RQM_SAFETY_MANUAL_ITEM

#### f61b1d964064b461a45784b5c88b001728c5ad99324f6ab538f908c1d2430efc
The user of MICROSAR Safe shall verify that the array static const WdgIf_InterfaceFunctionsPerWdgDeviceType WdgIf_FunctionsPerWdg [WDGIF_NUMBER_OF_WDGIFDEVICES] is defined in WdgIf_LCfg.c.
WdgIf_FunctionsPerWdg shall refer all – and only - the WD Interface Devices that are configured in the EDF.
WdgIf_FunctionsPerWdg[i] shall refer the underlying WD Interface Device in the EDF with WdgIfDeviceIndex = i.
The fields in an array element in WdgIf_FunctionsPerWdg shall be set as follows:
| Field | Value | Description |
| --- | --- | --- |
| 1st | &device_functions | If the underlying WD Interface Device is directly linked to a WD driver for device, then the field refers to the C-struct device_functions. |
| 1st | NULL_PTR | If the underlying WD Interface Device shares the WD driver with other WD Interface Devices using a state combiner, then the linked WD device is referred in wdgif_statecombiner_config. |
If a state combiner is configured, an array element in WdgIf_FunctionsPerWdg shall also contain the following field:
| Field | Value | Description |
| --- | --- | --- |
| 2nd | WdgInstance | A number that uniquely identifies the WD Interface Device instance for the underlying platform. All instances on the same platform are numbered consecutively starting with 0. Example: One platform has instances A and B, another platform has instances C and D. Then A, B, C, and D have WdgInstance set (in this order) as: 0,1,0,1. |
- ForeignTraceId: SMI-532
- ForeignAlternativeId: SMI-37F3BDFF-AFF1-4A2B-9DCC-45B8B6F4F14F
- ObjectType: RQM_SAFETY_MANUAL_ITEM

#### 6c1acab5309a76d60e73f754399fedafe0b5611d9b975c96311be7f9c9eefbfb
If a state combiner is configured, the user of MICROSAR Safe shall verify that the array static const WdgIf_StateCombinerConfigType wdgif_statecombiner_config is defined in WdgIf_LCfg.c.
The fields in wdgif_statecombiner_config shall be set as follows:
| Field | Value | Description |
| --- | --- | --- |
| 1st | WDGIF_NUMBER_OF_SLAVES | The number of configured slaves. |
| 2nd | WdgIfStateCombinerSpinlockID | Depending on configuration: Either the referenced OSSpinlock (WdgIfStateCombinerOSSpinlock) or the value of field WdgIfStateCombinerSpinlockID in the EDF. |
| 3rd | WdgIfStateCombinerStartUpSyncCycles | The value of field WdgIfStateCombinerStartUpSyncCycles in the EDF. |
| 4th | &device_functions | A reference to the WD driver API functions for device. |
| 5th | wdgif_statecombiner_shared_memory | A reference to the shared memory for the state combiners of the Watchdog Interfaces. |
| 6th | wdgif_statecombiner_slave_trigger_pattern | A reference to the array of the state combiners trigger pattern of each slave. |
- ForeignTraceId: SMI-533
- ForeignAlternativeId: SMI-D0CF8D85-4F84-4A54-A8E2-C55DDF325F94
- ObjectType: RQM_SAFETY_MANUAL_ITEM

#### 3317dcce2fcd703a67896d0ec5e58d25fe0e18b7e6999d27aefc50fc1a6c66ad
If a state combiner is configured, the user of MICROSAR Safe shall verify that the array WdgIf_StateCombinerSharedMemory wdgif_statecombiner_shared_memory [WDGIF_NUMBER_OF_SLAVES] is defined in WdgIf_LCfg.c.
The WdgIf writes to this array, hence it is not const.
wdgif_statecombiner_shared_memory shall contain one array element for each configured slave and the fields in the element shall be set as shown in the following table:
| Field | Value | Description |
| --- | --- | --- |
| 1st | 0u | Initial value for the slave’s counter. |
| 2nd | ~((uint32) 0u) | Inverse initial value for the slave’s counter. |
- ForeignTraceId: SMI-534
- ForeignAlternativeId: SMI-48BA373B-1791-4049-8BE7-98BC312E5455
- ObjectType: RQM_SAFETY_MANUAL_ITEM

#### 987c8a6849efcb58f80badc3a37704312ad9d08282283c2201d1722207e4c882
If the state combiner is configured, the user of MICROSAR Safe shall verify that for a configured slave with ID the C-struct static const WdgIf_StateCombinerSlaveTriggerPatternType wdgif_statecombiner_config_slave<ID> is defined in WdgIf_LCfg.c.
wdgif_statecombiner_config_slave<ID> shall be set as follows:
| Field | Value | Description |
| --- | --- | --- |
| 1st | WdgIfStateCombinerReferenceCycle | The value of field WdgIfStateCombinerReferenceCycle in the EDF. |
| 2nd | WdgIfStateCombinerSlaveIncrementsMin | The value of field WdgIfStateCombinerSlaveIncrementsMin in the EDF. |
| 3rd | WdgIfStateCombinerSlaveIncrementsMax | The value of field WdgIfStateCombinerSlaveIncrementsMax in the EDF. |
- ForeignTraceId: SMI-536
- ForeignAlternativeId: SMI-A455387C-360F-4C47-BAF8-4EB01AEDB258
- ObjectType: RQM_SAFETY_MANUAL_ITEM

#### 9d12f74441184ba79e9c3fe815b7da18c45ee7f42ce6fd46a8209c5fb2f71956
The user of MICROSAR Safe shall verify that for each configured platform the C-struct static const WdgIf_InterfaceFunctionsType <WdgIfDevice>_functions is defined in WdgIf_LCfg.c.
The fields for each C-struct <WdgIfDevice>_functions shall be set as follows:
| Field | Value | Description |
| --- | --- | --- |
| 1st | Wdg_<infix>_SetMode_ | A reference to the WD driver’s API function to set the mode of the device referred to by infix. |
| 2nd | Wdg_<infix>_SetTriggerCondition_ | A reference to the WD driver’s API function to set the trigger condition of the device referred to by infix. |
- ForeignTraceId: SMI-537
- ForeignAlternativeId: SMI-DB3FB24B-582E-4E5E-BDCA-D07C7E54E522
- ObjectType: RQM_SAFETY_MANUAL_ITEM

### 02d67397a7e83f03bdf0927ba8356b5bccbf694c6391187631ea8425ed09944d: Safety requirements required from other components
- ChapterNumber: 15.4
- ObjectType: DocItem

#### e1316c4f9c8f5cfada1eddce58d575de5d3cafa3ed8c907a22b32fad0b9ea6ec
This component requires the triggering of the watchdog and setting the triggering mode as a safety requirement from the watchdog driver.
This requirement is fulfilled if a watchdog driver by Vector is used.
- ForeignTraceId: SMI-520
- ForeignAlternativeId: SMI-EDF082B5-28B3-467A-B019-B2C460DD37D8
- ObjectType: RQM_SAFETY_MANUAL_ITEM

#### ae6391363e21a9ea58173194645dd6fc26f4f1a06faf883fa4887ae5e78e18fd
The WdgIf shall be used in order to call the services of underlying Watchdog driver(/s) to set the mode and the trigger condition as expected by the drivers.
The user of MICROSAR Safe shall verify that the WdgIf services are only called by the WdgM.
This requirement is fulfilled for all components of MICROSAR (if Vector's WdgM is used).
If e.g. the trigger condition is called by another component, this may lead to unintended triggering of the watchdog.
If the watchdog stack is not properly set up, it may not provide the expected protection.
- ForeignTraceId: SMI-3085
- ForeignAlternativeId: SMI-2CC9440D-69D5-4FE5-9530-9202D19B1252
- ObjectType: RQM_SAFETY_MANUAL_ITEM

### 3aab16cde910bc8f9cc70340d68e353f6c3c906f019f74624ea7c6da5dddfb16: Dependencies to hardware
- ChapterNumber: 15.5
- ObjectType: DocItem

#### b6fa263463479c0657518b6af7130f196dfd4c29bdf5a58b7010c2146e4f6ede
This component does not use a direct hardware interface.
- ObjectType: DocItem

## f644ed36a0043541ba93b73ac5bcec58e64c2f033c35b39826903c314c0f39f4: Safety Manual WdgM
- ChapterNumber: 16
- ObjectType: DocItem

### 96f884d72dec212b71bca584be0eac985471f2049d3c61fc8d69ea1df3d6c4ca: Assumed safety requirements
- ChapterNumber: 16.1
- ObjectType: DocItem

#### 5ce44b6f9b2d4c8e496a170084cf8c2aed471d1a8dbd6d5195f759f60193042b
This component assumes the following safety requirements:
| ID | Safety Requirement | Associated TSR | ASIL |
| --- | --- | --- | --- |
| CREQ-102743 | WdgM shall provide a service to initialize itself. | TSR-1 | ASIL D |
| CREQ-102747 | WdgM shall provide Supervised Entities. | TSR-14,TSR-15,TSR-13 | ASIL D |
| CREQ-102748 | WdgM shall provide Checkpoints. | TSR-15,TSR-14,TSR-13 | ASIL D |
| CREQ-102746 | WdgM shall provide a mechanism for Alive Supervision. | TSR-14 | ASIL D |
| CREQ-102745 | WdgM shall provide a mechanism for Deadline Supervision. | TSR-15 | ASIL D |
| CREQ-102744 | WdgM shall provide a mechanism for Logical Supervision. | TSR-13 | ASIL D |
| CREQ-102749 | WdgM shall provide a service to trigger a checkpoint. | TSR-13,TSR-15,TSR-14 | ASIL D |
| CREQ-102754 | WdgM shall provide a service to activate the supervision of a Supervised Entity. | TSR-13,TSR-15,TSR-14 | ASIL D |
| CREQ-102755 | WdgM shall provide a service to deactivate the supervision of a Supervised Entity. | TSR-14,TSR-13,TSR-15 | ASIL D |
| CREQ-102763 | WdgM shall provide a service to cyclically update the global supervision status. | TSR-14,TSR-13,TSR-15 | ASIL D |
| CREQ-102756 | WdgM shall provide modes. | TSR-15,TSR-14,TSR-13 | ASIL D |
| CREQ-102758 | WdgM shall provide a service to set a new trigger mode. | TSR-13,TSR-14,TSR-15 | ASIL D |
| CREQ-102764 | WdgM shall provide a global status DEACTIVATED. | TSR-14,TSR-13,TSR-15 | ASIL D |
| CREQ-102765 | WdgM shall provide a global status OK. | TSR-14,TSR-15,TSR-13 | ASIL D |
| CREQ-102766 | WdgM shall provide a global status FAILED. | TSR-15,TSR-14,TSR-13 | ASIL D |
| CREQ-102767 | WdgM shall provide a global status EXPIRED. | TSR-15,TSR-14,TSR-13 | ASIL D |
| CREQ-102768 | WdgM shall provide a global status STOPPED. | TSR-14,TSR-13,TSR-15 | ASIL D |
| CREQ-102769 | WdgM shall provide a supervised entity status DEACTIVATED. | TSR-14,TSR-13,TSR-15 | ASIL D |
| CREQ-102770 | WdgM shall provide a supervised entity status OK. | TSR-14,TSR-15,TSR-13 | ASIL D |
| CREQ-102771 | WdgM shall provide a supervised entity status FAILED. | TSR-15,TSR-13,TSR-14 | ASIL D |
| CREQ-102772 | WdgM shall provide a supervised entity status EXPIRED. | TSR-13,TSR-14,TSR-15 | ASIL D |
- ForeignTraceId: SMI-373
- ForeignAlternativeId: SMI-F906CE66-4127-47FC-B818-61C47D691146
- ObjectType: RQM_SAFETY_MANUAL_ITEM

#### af151450c14d4f2ceb2fd1a5a2d9dd21f0b0e5e787d709d0f3bf1e79020a6063
This component in addition to the assumed safety requirements ensures freedom from interference with respect to memory and timing with up to ASIL D.
- ObjectType: DocItem

#### 98a27868d9074f90f0ee790e1f72826383a5fd247cf5b93819d734d8a26261e7
The watchdog manager is able to detect program flow violations, alive counter violations and deadline violations.
The following types of faults can be detected:
- omission of an operation (program flow, alive counter),
- unrequested execution of an operation (program flow, alive counter),
- operation executed too early (alive counter, deadline),
- operation executed too late (alive counter, deadline), and
- operations executed in the wrong sequence (program flow).
- ObjectType: DocItem

### 61553ee651f59864a0293d4f77c9e8c4b771e0d7c324325b167bc915514bc4aa: Configuration constraints
- ChapterNumber: 16.2
- ObjectType: DocItem

#### 1add87d3d9b5bf5e902d6883cbe5ac46b7d546d42cc969c405a1dc60aade8143
The user of MICROSAR Safe shall use the WdgM only on 32-bit microcontroller platforms.
This requirement is necessary to ensure usage in a released configuration.
- ForeignTraceId: SMI-501
- ForeignAlternativeId: SMI-780FCA5D-966A-472C-8D68-D25F28CD17D0
- ObjectType: RQM_SAFETY_MANUAL_ITEM

#### f0c4de6ddaa9f1ea1e3e8e5dae160d5924a6b1644e15da445dfd279b16cd3f31
The user of MICROSAR Safe shall configure and verify alive supervision for a supervised entity.
If no alive supervision is configured for a supervised entity, WdgM cannot detect if the corresponding checkpoint is reached at least once.
Please note that for non-periodic supervised entities alive supervision is not possible.
This requirement is necessary to ensure usage in a released configuration.
- ForeignTraceId: SMI-499
- ForeignAlternativeId: SMI-01E68B4F-F69D-47E9-93B2-FEAC6878A021
- ObjectType: RQM_SAFETY_MANUAL_ITEM

#### 3b6a573b2a7501cdd14e8a9902cd92ff7470e483931a6e610793d619c31e2055
A value of a pre-compile configuration parameter is valid for every core. A different value cannot be set for the same pre-compile parameter and different cores.
- ObjectType: DocItem

#### c18084f43fc9af85b002778226565ef1aeb21fcae8983c62fa2605da618d3df2
The user of MICROSAR Safe shall set the value of WdgMTimebaseSource according to the required source of time ticks:
| WdgMTimebaseSource | Description |
| --- | --- |
| WDGM_INTERNAL_SOFTWARE_TICK | An internal time source for Deadline Monitoring is selected. The tick counter is incremented each time the WdgM_MainFunction() is invoked. |
| WDGM_OS_COUNTER_TICK | An OsCounter is selected for Deadline Monitoring as timebase. The user of MICROSAR Safe is responsible for configuring the OsCounter accurately. |
| WDGM_EXTERNAL_TICK | An external time source for Deadline Monitoring is selected. The tick counter is incremented each time the WdgM_UpdateTickCount() function is invoked. The function is implemented in the WdgM. The user of MICROSAR Safe is responsible for calling WdgM_UpdateTickCount() accurately. |
This requirement is necessary to ensure usage in a released configuration.
- ForeignTraceId: SMI-498
- ForeignAlternativeId: SMI-48A00108-7C8F-4474-B6A9-E794816D2C0A
- ObjectType: RQM_SAFETY_MANUAL_ITEM

#### 7aacacf03a7499fe1c9eb6ca1ec0fecc77a582e1a0a86696a9f23743ff36a785
The user of MICROSAR Safe shall use the functions WdgM_ActivateSupervisionEntity() and WdgM_DeactivateSupervisionEntity() to activate and deactivate the supervision of supervised entities.
Activation and deactivation shall only be performed by a software component that is developed according to the highest ASIL that is allocated to the ECU.
The functions are only available if WdgMEntityDeactivationEnabled is set to TRUE.
Vector recommends setting WdgMEntityDeactivationEnabled to FALSE to prevent that faults are not detected.
This requirement is necessary to ensure TSR-13, TSR-14 and TSR-15.
- ForeignTraceId: SMI-560
- ForeignAlternativeId: SMI-0BD235FF-412B-459C-80B8-4024674E50BC
- ObjectType: RQM_SAFETY_MANUAL_ITEM

### bfd43d17815c0886d46ebd4afc5b4d8808012a2a5e72160fb4a6a58748d90003: Additional verification measures
- ChapterNumber: 16.3
- ObjectType: DocItem

#### 8b854a66176f9d68e42eb2a2c17c7c17b67acaf9b2c2aa35edbe21a3a0d3a363
The user of MICROSAR Safe shall verify that the WdgM is initialized only at intended points in time, e.g. during initialization.
Unintended re-initialization may lead to a incorrect monitoring.
- ForeignTraceId: SMI-3072
- ForeignAlternativeId: SMI-BF504CB1-49CB-4A84-9E10-B2A46CF581F1
- ObjectType: RQM_SAFETY_MANUAL_ITEM

#### d544eed41932ec08a314a2cb89166a06902e5ef42a952662ebb0cbec17ad8a8b
The user of MICROSAR Safe shall inspect the messages of the generator execution.
If the generator aborts the generation process with an error message, the (partially) generated output files shall not be used in the system.
If the generator detects an error, a message starting with "ERROR" is displayed on the standard output.
If the generator shows a warning message starting with "WARNING", the user of MICROSAR Safe shall ensure that the cause of the warning does not invalidate the generated output files.
- ForeignTraceId: SMI-524
- ForeignAlternativeId: SMI-23BCC6CE-2BDD-4F2E-ACC3-2281A45FC0DE
- ObjectType: RQM_SAFETY_MANUAL_ITEM

#### bdfea9a9a7fa08fb9ad9025c0fbfddf67ae7daeebf718d56bd5c8b4996b1b62c
If WdgMStatusReportingMechanism is configured to be WDGM_USE_MODE_SWITCH_PORTS or WdgMStatusReportingMechanism is configured to be WDGM_USE_NOTIFICATIONS and WdgMUseRte is enabled an additional file with executable code is generated for each used core. Another precondition for the existence of the file is that there must be at least one parameter WdgMReportStatusViaRte of a WdgMMode or WdgMSupervisedEntity enabled (of the corresponding core).
The file is named WdgM_StatusNotifications_Core<CoreId>.c.
The user of MICROSAR Safe shall inspect the generated executable code. Notification functions are generated for each WdgMMode and WdgMSupervisedEntity if WdgMReportStatusViaRte is enabled. Only valid functions from Rte must be called within that notifications.
- ForeignTraceId: SMI-126207
- ForeignAlternativeId: SMI-3ED9D65E-E2AE-4767-BFFA-9DDD3D9458FB
- ObjectType: RQM_SAFETY_MANUAL_ITEM

#### 00b009d153a07cb3c148efa5bad3ac05f2b08c2d1044adae8310bff1ce4ce287
If WdgMTimebaseSource is configured to be WDGM_OS_COUNTER_TICK the user of MICROSAR Safe shall verify that the WdgMOsCounterMaxAllowedValue is correctly generated according to the referenced Os counter.
- ForeignTraceId: SMI-605940
- ForeignAlternativeId: SMI-8813D944-4995-453C-8CA8-B48EAE1C9BA8
- ObjectType: RQM_SAFETY_MANUAL_ITEM

#### 21a46489e833de888e996bddf4817e6bbe9a4304029c4003fa5c8ef438f530c0: Additional verification using WdgM Verifier
- ChapterNumber: 16.3.1
- ObjectType: DocItem

##### 812c3622b110ea6eec570a1c9b460a55b5c45d3028b82fcc5391770639c72a7c
The user of MICROSAR Safe shall execute the supplied WdgM Verifier.
Instructions can be found in the technical reference of WdgM on how to run the WdgM Verifier.
- ForeignTraceId: SMI-503
- ForeignAlternativeId: SMI-777C43F5-6ED8-40D4-A21F-B283F3083748
- ObjectType: RQM_SAFETY_MANUAL_ITEM

##### 4e2327f7ccd69417b4d1fbd76953df6c8738607b688343e7a989a7c19e66b5c1
The user of MICROSAR Safe shall verify that the report of the WdgM Verifier
- comprises "All tests passed" in the last line. and
- that all tests in the Summary of the report are marked with PASSED.
- ForeignTraceId: SMI-504
- ForeignAlternativeId: SMI-F3F63B4F-F70A-41F5-96B1-95FD75003D7B
- ObjectType: RQM_SAFETY_MANUAL_ITEM

##### 621522a3322e58ff64d85361ed14cc7e0b445150cb780dc03cce5322208fc06a
The user of MICROSAR Safe shall verify the generated local transitions in wdgm_verifier_info.c.
Generated local transitions are defined by the C-struct array with the name local_transitions.
The array holds all local transitions of all supervised entities.
Each local transition lt contains the names of:
- the source entity (SE) of lt,
- the source checkpoint of lt,
- the destination entity (SE) of lt and
- the destination checkpoint of lt.
Verification shall include that
- each local transition is defined as stated in the System Specification, and
- no local transition in the System Specification is missing.
- ForeignTraceId: SMI-512
- ForeignAlternativeId: SMI-299C9C38-C8F1-4860-AA16-B99DC6E6B717
- ObjectType: RQM_SAFETY_MANUAL_ITEM

##### b6df0629e09b5334e7f91380bd7171ec7c577375bdf508a440ab0105bf287ea3
The user of MICROSAR Safe shall verify the generated global transitions in wdgm_verifier_info.c.
Generated global transitions are defined by the C-struct array with the name global_transitions.
The array holds all global transitions of all supervised entities.
Each global transition gt contains the names of:
- the source entity (SE) of gt,
- the source checkpoint of gt,
- the destination entity (SE) of gt, and
- the destination checkpoint of gt.
Verification shall include that
- each global transition is defined as stated in the System Specification, and
- no global transition in the System Specification is missing.
- ForeignTraceId: SMI-513
- ForeignAlternativeId: SMI-4EB20FF0-F19D-4EFB-9BBE-AE71579F524F
- ObjectType: RQM_SAFETY_MANUAL_ITEM

##### 44c1f87635be5e99070f9370c8f3206009d8af7b1ba9de1d83170140a932405d
The user of MICROSAR Safe shall verify the checkpoints in wdgm_verifier_info.c.
Supervised entities named se are defined by a C-struct array with the name se_<se>_cp_list_.
The array se_<se>_cp_list_ holds information about all checkpoints configured for se.
Each array item contains information about one checkpoint cp of the supervised entity se:
- the supervised entity's ID (for this cp of se),
- the checkpoint's ID (for this cp of se),
- the supervised entity name (for this cp of se), and
- the checkpoint name (for this cp of se).
Verification shall include that
- each checkpoint is configured as stated in the System Specification, and
- no checkpoint for the actual supervised entity is missing.
- ForeignTraceId: SMI-514
- ForeignAlternativeId: SMI-0E6A3256-D4E5-4C9F-8BED-93E057134163
- ObjectType: RQM_SAFETY_MANUAL_ITEM

##### 2011b9bbf0c2da8400c903db5b58d279d9b737774167f0e9cac227eb9b3a274c
The user of MICROSAR Safe shall verify the supervised entities in wdgm_verifier_info.c.
Supervised entities named se are defined by a C-struct array with the name entities.
The array entities holds information about a configured supervised entity.
The fields in an array item for a supervised entity se shall have the following values (in this order):
| Value | Source Line Comment |
| --- | --- |
| The entity ID (of se). | enitity id |
| The entity name (of se). | entity name |
| The number of checkpoints configured for se. | number of checkpoints |
| A reference se_<se>_cp_list_, which refers to the list of CPs for se | this entity's checkpoints |
| A reference to the callback function for se as configured in WdgMLocalStateChangeCbk if WdgMStatusReportingMechanism is configured to be WDGM_USE_NOTIFICATIONS (otherwise NULL_PTR). | WdgMLocalStateChangeCbk |
| A reference to rte function for se if WdgMStatusReportingMechanism is configured to be WDGM_USE_MODE_SWITCH_PORTS (otherwise NULL_PTR). | WdgM_StatusReportToRte |
| false | autosar_3_1_x_compatibility |
| The application task for se as configured in field WdgMAppTaskRef | WdgMAppTaskRef |
Verification shall include that
- each supervised entity is configured as stated in the System Specification, and
- no supervised entity is missing.
- ForeignTraceId: SMI-515
- ForeignAlternativeId: SMI-EA1EE443-F21C-4160-B045-80369A5CF44E
- ObjectType: RQM_SAFETY_MANUAL_ITEM

##### 9025cc87c7eb0f2a97f5a33aaf19b6345bbe7f1216e4c0e33be9d4c06e525c38
The user of MICROSAR Safe shall verify the deadline supervisions in wdgm_verifier_info.c.
Deadline supervisions are defined by a C-struct array with the name deadline_supervisions.
The array deadline_supervisions holds information about all transitions with deadline supervision.
Each deadline supervision dl contains the following values:
- the source entity name (SE) of dl,
- the source checkpoint name of dl,
- the destination entity name (SE) of dl,
- the destination checkpoint name of dl,
- the minimum deadline for dl (in seconds), and
- the maximum deadline of dl (in seconds).
Verification shall include that
- each deadline supervision is configured as stated in the System Specification, and
- no deadline supervision is missing.
- ForeignTraceId: SMI-516
- ForeignAlternativeId: SMI-B39408DD-4B2D-4CF9-BBB7-71F6E945229E
- ObjectType: RQM_SAFETY_MANUAL_ITEM

##### 9b873c02bf607182c91c7ff43b778c983cee885ce2bcb815ccfcabc911b04060
The user of MICROSAR Safe shall verify the alive supervisions in wdgm_verifier_info.c.
Alive supervisions are defined by a C-struct array with the name alive_supervisions.
The array alive_supervisions holds information about all transitions with alive supervision.
Each alive supervision al contains the following values:
- the supervised entity name (SE) of al,
- the checkpoint name of that se of al,
- the number of expected alive indications per reference cycle of al,
- the minimum margin for alive indications of al,
- the maximum margin for alive indications of al, and
- the number of supervision reference cycle of al.
Verification shall include that
- each alive supervision is configured as stated in the System Specification, and
- no alive supervision is missing.
- ForeignTraceId: SMI-517
- ForeignAlternativeId: SMI-11CC3D6E-7A3F-4F47-8B5C-A223CCEF3346
- ObjectType: RQM_SAFETY_MANUAL_ITEM

##### aa15a567fa57fa11bdf9d5bb4593565864712956ae885f5ff1a459f77042a032
The user of MICROSAR Safe shall verify the configured cores in wdgm_verifier_info.c.
The configured cores are defined in the main() function.
For each configured core with ID, the following line shall be present:
result += verify (&WdgMConfig_Modem_core<ID>, &verifier_info);
where ID is the core ID and m is the ID of the WdgM mode.
Verification shall include that for each core there is a corresponding line in the file.
- ForeignTraceId: SMI-518
- ForeignAlternativeId: SMI-6CE5E25C-AA20-4FAB-9BEF-36E089EF6409
- ObjectType: RQM_SAFETY_MANUAL_ITEM

#### 9267ab30948524bb49d34248e0bedefc7048a07199fec17697d113bef017b8d7: Additional verification of generator execution
- ChapterNumber: 16.3.2
- ObjectType: DocItem

##### 3e197e1e356dd7f618a32108c475f10fe1cb12b11d0dbe5c3f5f519d14f35a6e
The user of MICROSAR Safe shall verify that for the following arrays in WdgM_Cfg.c, the array length matches the number of items in the array:
- WdgMTransition
- WdgMGlobalTransition
- all arrays named StartsGlobalTransition<se>_<cp>_<i>_ (for a supervised entity se, a checkpoint cp and an integer i)
- WdgMCheckPoint
- WdgMSupervisedEntity
- all arrays named WdgMTriggerMode_core<ID> (for each core with ID)
- WdgMWatchdogDevice<ID> (for each core with ID)
- WdgMAllowedCallers
Some of these arrays have preprocessor defines for their size, e.g. WdgMCheckPoint [WDGM_NR_OF_CHECKPOINTS]. These defines can be found in WdgM_Cfg.h.
- ForeignTraceId: SMI-506
- ForeignAlternativeId: SMI-B0C19999-07EE-49DD-9DD9-8951942E7357
- ObjectType: RQM_SAFETY_MANUAL_ITEM

##### 158f515288e5637f8d9b37f0fcd285317d70096aae28516fa26db1988443e4d3
The user of MICROSAR Safe shall verify that each item in the array WdgMSupervisedEntity follows the rule:
- WdgMCheckpointRef has a value of the form _&WdgMCheckPoint[i] with i < WDGM_NR_OF_CHECKPOINTS, and
The array can be found in WdgM_Cfg.c.
- ForeignTraceId: SMI-507
- ForeignAlternativeId: SMI-70EFA246-4EFD-4C39-B7C4-8F0375E091CE
- ObjectType: RQM_SAFETY_MANUAL_ITEM

##### 38d559880a6fef239143b662d46d007504393c641d48979baf481517017a0a0c
The user of MICROSAR Safe shall verify that each WdgM_StatusReportToRte member of struct WdgM_ConfigType and each WdgM_StatusReportToRte member of struct WdgM_SupervisedEntityType has a valid entry if WDGM_STATUS_REPORTING_MECHANISM is set to WDGM_USE_MODE_SWITCH_PORTS.
The functions must be implemented by the Rte and must have the following signature: Std_ReturnType (*WdgM_StatusReportToRte) (WdgMMode).
Both structs can be found in WdgM_Cfg.c.
- ForeignTraceId: SMI-27923
- ForeignAlternativeId: SMI-EF77B8B3-8C95-4696-9E08-FEED1ABF5AF3
- ObjectType: RQM_SAFETY_MANUAL_ITEM

##### c81f29b0d7a7f01ff97c61e7d8e5ce150d9413d5853c9107c7b52179b847c6b0
The user of MICROSAR Safe shall verify that for each core with ID WDGM_NR_OF_WATCHDOGS_CORE<ID> matches the actual number of configured WD devices.
The define can be found in WdgM_Cfg.h.
- ForeignTraceId: SMI-508
- ForeignAlternativeId: SMI-FCA9BB06-9AF4-46C7-9BB0-33331216FD52
- ObjectType: RQM_SAFETY_MANUAL_ITEM

##### 9be9ce96899c9bad845b4635ea809a2fc12da823e8466e46707b4483012e6bf5
The user of MICROSAR Safe shall verify that for each core with ID WDGM_NR_OF_TRIGGER_MODES_CORE<ID> matches the actual number of configured Watchdog Manager Trigger Modes.
The define can be found in WdgM_Cfg.h.
- ForeignTraceId: SMI-509
- ForeignAlternativeId: SMI-7E28DE5D-C428-4F46-8405-3DF0FDFB2C3D
- ObjectType: RQM_SAFETY_MANUAL_ITEM

##### d31523ec7a445015c4c8ba0165ca6a206d514306a40ff4f2ffb49149fbfe6b39
The user of MICROSAR Safe shall verify that WDGM_NR_OF_ALLOWED_CALLERS matches the number of modules that call function WdgM_SetMode().
The define can be found in WdgM_Cfg.h.
- ForeignTraceId: SMI-510
- ForeignAlternativeId: SMI-7B0F7D61-DEA7-41D1-B77F-870140898738
- ObjectType: RQM_SAFETY_MANUAL_ITEM

##### 6789a3fafa7468e08760d6b9e09ec13af9e92a253fa2a7ace7eaf284a45d2c07
The user of MICROSAR Safe shall verify that in WdgMConfig_Mode<m>_core<ID> (for each core with ID and every mode m), the field WdgMCallersRef points to WdgMAllowedCallers and WdgMAllowedCallers is an array of type WdgM_CallersType with a length of WDGM_NR_OF_ALLOWED_CALLERS.
The variable can be found in WdgM_Cfg.h.
- ForeignTraceId: SMI-511
- ForeignAlternativeId: SMI-4B2669C6-5426-48F4-B530-2CFD1D6E0B2B
- ObjectType: RQM_SAFETY_MANUAL_ITEM

##### 8b4c953a39ed631743209fede6357755223f01d3f23a09f256807aa9e9e64d6c
The user of MICROSAR Safe shall verify the types used by WdgM.
If the configuration parameter WDGM_USE_RTE is set to STD_ON, the types from Rte_Type.h are used:
| Type | Allowed Value |
| --- | --- |
| WdgM_SupervisedEntityIdType | uint16 |
| WdgM_CheckpointIdType | uint16 |
| WdgM_ModeType | uint8 |
| WdgM_LocalStatusType | uint8 |
| WdgM_GlobalStatusType | uint8 |
The WdgM includes WdgM_Rte_Includes.h if and only if WDGM_USE_RTE is set to STD_ON.
If the configuration parameter WDGM_USE_RTE is set to STD_OFF, the types from WdgM are used:
| Type | Allowed Value |
| --- | --- |
| WdgM_SupervisedEntityIdType | uint16 |
| WdgM_CheckpointIdType | uint16 |
| WdgM_ModeType | uint8 |
| WdgM_LocalStatusType | uint8 |
| WdgM_GlobalStatusType | uint8 |
- ForeignTraceId: SMI-550
- ForeignAlternativeId: SMI-695F26C8-3B25-45D3-9D09-8B2A90E42E07
- ObjectType: RQM_SAFETY_MANUAL_ITEM

##### c797d2c0b7e379214d0145c618f8e453877efae0047a5a18cd018eba2b3550dc
The user of MICROSAR Safe shall verify the definitions used by WdgM.
If the configuration parameter WDGM_USE_RTE is set to STD_ON, the definitions from Rte_WdgM_Type.h are used.
If the configuration parameter WDGM_USE_RTE is set to STD_OFF, the definitions from WdgM are used.
| Definition | Value |
| --- | --- |
| WDGM_LOCAL_STATUS_OK | 0 |
| WDGM_LOCAL_STATUS_FAILED | 1 |
| WDGM_LOCAL_STATUS_EXPIRED | 2 |
| WDGM_LOCAL_STATUS_DEACTIVATED | 4 |
| WDGM_GLOBAL_STATUS_OK | 0 |
| WDGM_GLOBAL_STATUS_FAILED | 1 |
| WDGM_GLOBAL_STATUS_EXPIRED | 2 |
| WDGM_GLOBAL_STATUS_STOPPED | 3 |
| WDGM_GLOBAL_STATUS_DEACTIVATED | 4 |
The WdgM includes Rte_WdgM_Type.h if and only if WDGM_USE_RTE is set to STD_ON.
- ForeignTraceId: SMI-551
- ForeignAlternativeId: SMI-3C5E0A0B-7EFD-451F-94AD-9CEF426FC4BE
- ObjectType: RQM_SAFETY_MANUAL_ITEM

### ee61789554f3afabca6580cff638c835fd207fa2463ee5ae8dd8e6b432c9dc94: Safety requirements required from other components
- ChapterNumber: 16.4
- ObjectType: DocItem

#### 07d85409ce698cffb26fb9021be107272abe9d4472cfbcf361e57a769f8c352e
This component requires setting a trigger condition and setting the triggering mode as an assumed safety requirement (TSR-13, TSR-14, TSR-15) from WdgIf component.
For components provided as part of MICROSAR Safe, the respective section of the Safety Manual for that component allows you identifying if this requirement is fulfilled.
- ForeignTraceId: SMI-372
- ForeignAlternativeId: SMI-162BFD88-95C9-4443-8CC9-B2B81E903381
- ObjectType: RQM_SAFETY_MANUAL_ITEM

#### 151be1484196d11e9a8b9d1395829080c98364c1bd8cb43e4978e28628136d20
The user of MICROSAR Safe shall call the service to set the mode as expected by the Wdg stack.
If the watchdog is not properly set up, it may not provide the expected protection.
- ForeignTraceId: SMI-3414
- ForeignAlternativeId: SMI-D28AC4B5-CFED-4F38-99D4-F088BF8715B0
- ObjectType: RQM_SAFETY_MANUAL_ITEM

### 9380c47247d785efc107832d2ea81722dfb1a8422883a7419ee24fcd65c7ced0: Dependencies to hardware
- ChapterNumber: 16.5
- ObjectType: DocItem

#### 19c55ed0443e718c29ce2ec877fce7800e4999776abdd6bc5fd4113be2e9481c
This component does not use a direct hardware interface.
- ObjectType: DocItem

## c71156ff8c60d68a46aa8a165d9d0dfc2b16dfe7596b4e7645c19a2a3047cb06: Glossary and Abbreviations
- ChapterNumber: 17
- ObjectType: DocItem

### 7d7fa20f39f678696ebd1e96095c68e62261bf8c9a5e48660230fd0bb9f289f3: Glossary
- ChapterNumber: 17.1
- ObjectType: DocItem

#### 24f18768aa92b5cc3dd8f4ba19e9f1d326a951f2d799c25240ede52b55576cbc
| Term | Definition |
| --- | --- |
| User of MICROSAR Safe | Integrator and user of components from MICROSAR Safe provided by Vector. |
| MICROSAR Safe | MICROSAR Safe comprises MICROSAR SafeBSW and MICROSAR SafeRTE as Safety Element out of Context. MICROSAR SafeBSW is a set of components, that are developed according to ISO 26262 [1], and are provided by Vector in the context of this delivery. The list of MICROSAR Safe components in this delivery can be taken from the documentation of the delivery. |
| Critical section | A section of code that needs to be protected from concurrent access. A critical section may be protected by using the AUTOSAR exclusive area concept. |
| Configuration data | Data that is used to adapt the MICROSAR Safe component to the specific use-case of the user of MICROSAR Safe. Configuration data typically comprises among others: feature selection, routing tables, channel tables, task priorities, memory block descriptions. |
| Generated code | Source code that is generated as a result of the configuration in DaVinci Configurator Pro |
| Partition | A set of memory regions that is accessible by tasks and ISRs. Synonym to OSApplication. |
- ForeignTraceId: OBJ538
- ForeignAlternativeId: OBJ-D156DDAB-151A-4985-9B54-7A47CAA3ED45
- ObjectType: TRACE_ITEM

### 70de2143613ec050d613c486321096a6e9bdb0dee33532c601c2d6de0862d3ae: Abbreviations
- ChapterNumber: 17.2
- ObjectType: DocItem

#### d5210a6c843aa70098ab6a05092f7d1d9a7094690dbc0557f67aca84e8a28de1
| Abbreviation | Description |
| --- | --- |
| ASIL | Automotive Safety Integrity Level |
| BSWMD | Basic Software Module Description |
| CPU | Central Processing Unit |
| CREQ | Component Requirement |
| EEPROM | Electronically Erasable and Programmable Read-only Memory |
| ECC | Error Correcting Code |
| ECU | Electronic Control Unit |
| EXT | Driver for an external hardware unit |
| ISO | International Standardization Organization |
| MCAL | Microcontroller Abstraction |
| MIP | Module Implementation Prefix |
| MSSV | MICROSAR Safe Silence Verifier |
| OS | Operating System |
| PDU | Protocol Data Unit |
| QM | Quality Management |
| RAM | Random Access Memory |
| SMI | Safety Manual Item |
| TCL | Tool Confidence Level |
- ObjectType: DocItem

## 3640461049cb0043d3af88f310070276ed6221cf2989f91a13c95c60976a584b: Contact
- ChapterNumber: 18
- ObjectType: DocItem

### 5971e8de7c6b309047cd954b1d5731d1c0c02b7c3c8569b40534631bb10b3a5d
Visit our website for more information on
- News
- Products
- Demo software
- Support
- Training data
- Addresses
www.vector.com
- ObjectType: DocItem
